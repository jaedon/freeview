OC-STB-HOST-MIB DEFINITIONS ::= BEGIN

IMPORTS
    TenthdB,
    TenthdBmV
        FROM DOCS-IF-MIB                    -- RFC 2670
    OBJECT-GROUP,
    MODULE-COMPLIANCE
        FROM SNMPv2-CONF                    -- RFC 2580
    Integer32,
    Unsigned32,
    Counter32,
    TimeTicks,
    OBJECT-TYPE,
    MODULE-IDENTITY,
    OBJECT-IDENTITY
        FROM SNMPv2-SMI                     -- RFC 2578
    AutonomousType,
    DisplayString,
    TruthValue,
    RowPointer,
    TimeStamp,
    PhysAddress,
    MacAddress,
    DateAndTime,
    TEXTUAL-CONVENTION
        FROM SNMPv2-TC                      -- RFC 2579
    SnmpAdminString
        FROM SNMP-FRAMEWORK-MIB             -- RFC 3411
    InetAddressType,
    InetAddress
        FROM INET-ADDRESS-MIB               -- RFC 4001
    hrDeviceIndex
        FROM HOST-RESOURCES-MIB             -- RFC 2790
    clabProjOpenCable
        FROM CLAB-DEF-MIB
        ;

ocStbHostMibModule MODULE-IDENTITY
    LAST-UPDATED "201102040000Z"        -- February 4, 2011
    ORGANIZATION "Cable Television Laboratories, Inc."
    CONTACT-INFO
         "Postal: Cable Television Laboratories, Inc.
         858 Coal Creek Circle
         Louisville, Colorado 80027-9750
         U.S.A.
         Phone: +1 303-661-9100
         Fax:    +1 303-661-9199
         E-mail: mibs@cablelabs.com"
    DESCRIPTION
            "This MIB module contains the management objects for the
            management of OpenCable Set-top Host Device."
    REVISION "201102040000Z"        -- February 4, 2011
    DESCRIPTION
            "Added S3D support with ocStbHostDVIHDMISupported3DStructures
            and ocStbHostDVIHDMIActive3DStructure.
            Added ocStbHostFirmwareDownloadGroupId.
            Added ocStbHostDVIHDMI3DCompatibilityControl,
            ocStbHostDVIHDMI3DCompatibilityMsgDisplay,
            ocStbHostSoftwareApplicationInfoSigLastNetworkVersionRead,
            ocStbHostSoftwareApplicationInfoSigVersionInUse."
    REVISION "201005070000Z"        -- May 7, 2010
    DESCRIPTION
            "Deprecated ocStbHostSoftwareApplicationSigStatus
            and added replacement leaf objects,
            ocStbHostSoftwareApplicationInfoSigLastReceivedTime
            and ocStbHostSoftwareApplicationInfoSigLastReadStatus.
            Added ocStbHostFirmwareDownloadFailedCount.
            Added ochdtc(7) to ocStbHostCapabilities, other(4) to
            ocStbHostFirmwareCodeDownloadStatus, and
            ocStbHostDVIHDMIEdidVersion."
    REVISION "200912110000Z"        -- December 11, 2009
    DESCRIPTION
            "Added ocStbHostDVIHDMIPreferredVideoFormat,
            ocStbHostDVIHDMIAvailableVideoFormatTable,
            ocStbHostAvcSupport, and
            ocStbHostCardSnmpAccessControl. Also removed
            extraneous ',' in HDMI Features object."
    REVISION "200909040000Z"        -- September 4, 2009
    DESCRIPTION
            "Added 'other(6)' enumerated value to
            ocStbHostDVIHDMIAttachedDeviceType, changed
            ocStbHostSoftwareApplicationSigStatus SYNTAX to
            enumerated values(INTEGER)."
    REVISION "200905080000Z"        -- May 8, 2009
    DESCRIPTION
            "Added HDMI objects ocStbHostDVIHDMIEdid,
            ocStbHostDVIHDMILipSyncDelay,
            ocStbHostDVIHDMICecFeatures,
            ocStbHostDVIHDMIFeatures,
            ocStbHostDVIHDMIMaxDeviceCount.
            Added the following objects to support the enhanced
            diagnostics display: ocStbHostDVIHDMIAttachedDeviceType,
            ocStbHostSoftwareFirmwareReleaseDate,
            ocStbHostSoftwareOrganizationId,
            ocStbHostSoftwareApplicationId,
            ocStbHostSoftwareApplicationSigStatus,
            ocStbHostPatTimeoutCount,
            ocStbHostPmtTimeoutCount,
            ocStbHostOobCarouselTimeoutCount,
            ocStbHostInbandCarouselTimeoutCount,
            ocStbHostCardOpenedGenericResource,
            ocStbHostCardTimeZoneOffset,
            ocStbHostCardDaylightSavingsTimeDelta,
            ocStbHostCardDaylightSavingsTimeEntry,
            ocStbHostCardDaylightSavingsTimeExit,
            ocStbHostCardEaLocationCode,ocStbHostCardVctId,
            ocStbHostCardCpAuthKeyStatus,
            ocStbHostCardCpCertificateCheck,
            ocStbHostCardCpCciChallengeCount,
            ocStbHostCardCpKeyGenerationReqCount,
            ocStbHostCardCpIdList,ocStbHostBootStatus,
            ocStbHostInBandTunerBandwidth.
            Added frameRate enumeration of 60Hz to
            ocStbHostDVIHDMIFrameRate.
            Added DateAndTime textual convention import."
    REVISION "200902060000Z"        -- February 6, 2009
    DESCRIPTION
            "Added 1) Notification support to MIB Notifications
            section, 2) a trap for signaling the headend a dump is
            ready to be transferred, 3) ocStbHostDumpEventCount,
            ocStbHostDumpNow, ocStbHostDumpEventTimeout, and
            ocStbHostDumpFilePath objects for Panic Dump transfer
            support, 4) new group and trap to the Notifications
            conformance section, 5) ocStbHostCfrSpecificationIssue and
            ocStbHostMibSpecificationIssue to report the versions of
            the specifications implemented,
            6) ocStbHostSystemTempMaxValue,
            7)ocStbHostSystemMemoryReportMemoryType and
            ocStbHostSoftwareStatus Objects to the compliance
            section to track obsoleted values.
            Modified 1) ocStbHostSoftwareStatus with new enumerated
            values, 2) ocStbHostInBandTunerPower to read-only
            MAX-ACCESS and 3) ocStbHostCardMfgId by changing SA
            to Cisco and adding Conax."
    REVISION "200811140000Z"        -- November 14, 2008
    DESCRIPTION
            "Added/updated tables to align the MIB with the CCIF
            Diagnostic APDU. Added color space, sample size, and
            frame rate to the ocStbHostDVIHdmiTable, additional memory
            types to the ocStbHostSystemMemoryReportTable, SNMP
            proxy objects, and added Out of Band messaging mode object.
            Corrected ocStbHostCCApplicationType to include 0 as a
            valid index. Modified descriptions to clarify usage of
            ocStbHostMpeg2ContentDecoderPTS, ocStbHostCASystemId,
            ocStbHostCardIpAddressType, and ocStbHostCardIpAddressIp.
            Added TotalTuneCount, TuneFailureCount, and
            TuneFailureFreq columns in
            ocStbHostInBandTunerTable to support field
            diagnostics. Added OIDs for CableCARD ID, CableCARD/Host
            binding status. Deprecated homenetworking and
            ocStbHostSecurityIdentifier objects. Corrected UNITS for
            objects with tenthdB syntax."
    REVISION "200803280000Z"        -- March 28, 2008
    DESCRIPTION
            "Corrected index for ocStbHostSoftwareApplicationInfoTable
            that required adding an index object. Added
            ocStbHostRebootInfo, ocStbHostMemoryInfo, ocStbHostJVMInfo.
            Also repaired a problem in two areas where OID values were
            changed from previous HOSTMIB I02 version. These include
            realignment of objects within the ocStbHostDVIHDMITable and
            ocStbHostFirmwareDownloadStatus. Added 1080p(5) to the
            VideoOutputFormat textual convention; updated the
            ocStbHostAvInterfaceTypes Description field to
            reference the DVIHDMI and 1394 tables; corrected INTEGER
            syntax statements to specify ranges. This version is
            published as part of the OpenCable Host MIB specification,
            MIB-HOST2.X, version I04. Copyright 1999-2008 Cable
            Television Laboratories, Inc. All rights reserved."
    REVISION "200711130000Z"        -- November 13, 2007
    DESCRIPTION
            "Added diagnostics MIB objects to include Home Network
            Table, MemoryReportTable, Software App Table and addition
            of software info MIB objects. Added diagnostics MIB objects
            to include Firmware download
            fail status, device HDCP status, fixed inband tuner
            interleaver object, added host DRI interface, Host
            capabilities, RDC data rate object, added MacAddress syntax
            to imports from rfc2579, changes syntax on RDC and FDC
            power level MIB objects to TenthdBmV, changed the index in
            ocStbHostCCAppInfoTable. This version is published as part
            of the OpenCable Host MIB specification, MIB-HOST2.X,
            version I03. Copyright 1999-2007 Cable Television
            Laboratories, Inc. All rights reserved."
    REVISION "200709210000Z"        -- September 21, 2007
    DESCRIPTION
            "Updated version to cover the addition of
            physical address, address type, ip address and subnetmask
            mib objects to both ocStbCardInfo and ocStbHostInfo,
            Tuner status MIB objects to ocStbHostInBandTunerState,
            MIB Decoder objects to ocStbHostMpeg2ContentTable,
            QAM statistics MIB objects to ocStbHostQPSK,
            CableCard Diagnostics ocStbHostCCMMITable and
            ocStbHostCCAppInfo. This version is published as part of
            the OpenCable Host MIB specification MIB-HOST2.X,
            version I02. Copyright 1999-2007 Cable Television
            Laboratories, Inc. All rights reserved."
    ::= { clabProjOpenCable 1 }

--
-- Textual conventions
--

VideoOutputFormat ::= TEXTUAL-CONVENTION
    STATUS      current
    DESCRIPTION
            "Defines the output format of the video signal
            horizontal and vertical resolution."
    SYNTAX      INTEGER {
                format480i(1),
                format480p(2),
                format720p(3),
                format1080i(4),
                format1080p(5)
                }

AudioOutputFormat ::= TEXTUAL-CONVENTION
    STATUS      current
    DESCRIPTION
            "Defines the output format of the audio signal."
    SYNTAX      INTEGER
                {
                other(1),
                lpcm(2), -- CD-A, DVD-A
                ac3(3), -- Dolby Digital
                eac3(4), -- Dolby Digital Plus
                mpeg1L1L2(5), -- MPEG-1 Layers 1 & 2
                mpeg1L3(6), -- MPEG-1 Layer 3
                mpeg2(7), -- Advanced Audio Coding (AAC-LC)
                mpeg4(8), -- MPEG-4 Advanced Audio Coding
                          -- High Efficiency (AAC PLUS)
                dts(9), -- Digital Theater Sound
                atrac(10) -- Adaptive Transform Acoustic Coding
                }

VideoAspectRatio ::= TEXTUAL-CONVENTION
    STATUS      current
    DESCRIPTION
            "Defines the horizontal and vertical aspect ratio of the
            video signal.
            'fourByThree' means a 4 by 3 aspect ratio.
            'sixteenByNine' means a 16 by 9 aspect ratio.
            'other' indicates a non-specified aspect ratio."
    SYNTAX      INTEGER {
                other(1),
                fourByThree(2),
                sixteenByNine(3)
                }

--
-- Node definitions
--

ocStbHostNotifications OBJECT IDENTIFIER ::= { ocStbHostMibModule 0 }
ocStbPanicDumpTrap NOTIFICATION-TYPE
    OBJECTS {
             ocStbHostDumpFilePath
            }
    STATUS      current
    DESCRIPTION
            "Notifies host that a panic dump condition has occurred.
            The headend then may issue a TFTP Get to retrieve the
            dump or ignore the trap and allow the host
            ocStbHostDumpEventTimeout timer to expire. This trap is
            sent only when the ocStbHostDumpEventCount object has a
            non-zero value."
    ::= { ocStbHostNotifications 1 }

ocStbHostMibObjects OBJECT IDENTIFIER ::= { ocStbHostMibModule 1 }

ocStbHostSystem OBJECT IDENTIFIER ::= { ocStbHostMibObjects 1 }
ocStbHostHWIdentifiers OBJECT IDENTIFIER ::= { ocStbHostSystem 1 }
ocStbHostInterfaces OBJECT IDENTIFIER ::= { ocStbHostSystem 2 }

ocStbHostSerialNumber OBJECT-TYPE
    SYNTAX      SnmpAdminString
    MAX-ACCESS read-only
    STATUS      current
    DESCRIPTION
            "The manufacturer's serial number for this device."
    ::= { ocStbHostHWIdentifiers 1 }

ocStbHostHostID OBJECT-TYPE
    SYNTAX      DisplayString (SIZE(17))
    MAX-ACCESS read-only
    STATUS      current
    DESCRIPTION
            "Allows the manager to retrieve the 40-bit Host ID
            of the ocStbHost (SNMP apdu TLV #1) in the string
            format indicated below:

           M-MMU-UUU-UUU-UUL

           Where:

           M-MM is the decimal representation of the
           10-bit CHICA assigned manufacturer number.

           U-UUU-UUU-UU is the decimal representation
           of the 30-bit manufacturer assigned unit number.

           L is a Luhn check digit calculated over the
           preceding 12 decimal digits.

            If the Host ID is unknown, then the string shall
            be all zeros e.g., '0-000-000-000-000'."
    ::= { ocStbHostHWIdentifiers 2 }

ocStbHostCapabilities OBJECT-TYPE
    SYNTAX      INTEGER {
                other(1),
                ochd2(2),
                embedded(3),
                dcas(4),
                ochd21(5),
                bocr(6),
                ochdtc(7)
                }
    MAX-ACCESS read-only
    STATUS      current
    DESCRIPTION
            "The capabilities indication of the STB device.

           'other' means a device which is not described
               by one of the other enumerations in this list.
           'ochd2' means the STB device is an OpenCable Host Device
                Version 2 Compliant device.
            'embedded' means the STB device is of the non-removable
                security type.
            'dcas' means the STB device is of the downloadable
                security type.
            'ochd21' means the STB device is an OpenCable Host Device
                Version 2.1 Compliant device.
            'bocr' means the STB is bi-directional OCUR compliant.
            'ochdtc' means the STB is an OpenCable Host Thin Chassis
                device."
    ::= { ocStbHostHWIdentifiers 3 }

ocStbHostAvcSupport OBJECT-TYPE
    SYNTAX      TruthValue
    MAX-ACCESS read-only
    STATUS      current
    DESCRIPTION
            "The AVC capabilities indication of the STB device.
            The object has a value of true (1) if AVC decode is
            supported. Otherwise, the object has a value of false (2).
            The object is required when the ocStbHostCapabilities value
            is ochd(2); otherwise the object is optional."
    ::= { ocStbHostHWIdentifiers 4 }

-- Types appropriate for use when designating devices and interfaces
-- related to OpenCable Hosts. These types, for example, can be used
-- in ocStbHostAVInterfaceType to designate the kind of interface.
-- These types are also appropriate for use in hrDeviceType.
--
--
ocStbHostDevInterfaceTypes OBJECT IDENTIFIER ::= { ocStbHostInterfaces 1 }

ocStbHostOther OBJECT-IDENTITY
    STATUS      current
    DESCRIPTION
            "The type identifier used for an interface not defined
            in this MIB."
    ::= { ocStbHostDevInterfaceTypes 1 }

ocStbHostScte55FdcRx OBJECT-IDENTITY
    STATUS      current
    DESCRIPTION
            "The type identifier used for SCTE-55 FDC Receiver
            (i.e., out-of-band downstream tuner)."
    ::= { ocStbHostDevInterfaceTypes 2 }

ocStbHostScte55RdcTx OBJECT-IDENTITY
    STATUS      current
    DESCRIPTION
            "The type identifier used for SCTE-55 RDC Transmitter
            (i.e., out-of-band upstream transmitter)."
    ::= { ocStbHostDevInterfaceTypes 3 }

ocStbHostScte40FatRx OBJECT-IDENTITY
    STATUS      current
    DESCRIPTION
            "The type identifier used for SCTE-40 FAT Receiver
            (i.e., in-band video tuner)."
    ::= { ocStbHostDevInterfaceTypes 4 }

ocStbHostBbVideoIn OBJECT-IDENTITY
    STATUS      current
    DESCRIPTION
            "The type identifier used for baseband video input."
    ::= { ocStbHostDevInterfaceTypes 5 }

ocStbHostBbAudioIn OBJECT-IDENTITY
     STATUS      current
     DESCRIPTION
             "The type identifier used for baseband audio input."
     ::= { ocStbHostDevInterfaceTypes 6 }

ocStbHostBbVideoOut OBJECT-IDENTITY
    STATUS      current
    DESCRIPTION
            "The type identifier used for baseband video output."
    ::= { ocStbHostDevInterfaceTypes 7 }

ocStbHostBbAudioOut OBJECT-IDENTITY
    STATUS      current
    DESCRIPTION
            "The type identifier used for baseband audio output."
    ::= { ocStbHostDevInterfaceTypes 8 }

ocStbHostRfOutCh OBJECT-IDENTITY
    STATUS      current
    DESCRIPTION
            "The type identifier used for analog RF output."
    ::= { ocStbHostDevInterfaceTypes 9 }

ocStbHostSVideoIn OBJECT-IDENTITY
    STATUS      current
    DESCRIPTION
            "The type identifier used for SVideo input."
    ::= { ocStbHostDevInterfaceTypes 10 }

ocStbHostSVideoOut OBJECT-IDENTITY
    STATUS      current
    DESCRIPTION
            "The type identifier used for SVideo output."
    ::= { ocStbHostDevInterfaceTypes 11 }

ocStbHostComponentIn OBJECT-IDENTITY
    STATUS      current
    DESCRIPTION
            "The type identifier used for Component input."
    ::= { ocStbHostDevInterfaceTypes 12 }

ocStbHostComponentOut OBJECT-IDENTITY
    STATUS      current
    DESCRIPTION
            "The type identifier used for Component output."
    ::= { ocStbHostDevInterfaceTypes 13 }

ocStbHostDviIn OBJECT-IDENTITY
    STATUS      current
    DESCRIPTION
            "The type identifier used for DVI input."
    ::= { ocStbHostDevInterfaceTypes 14 }

ocStbHostDviOut OBJECT-IDENTITY
    STATUS      current
    DESCRIPTION
            "The type identifier used for DVI output."
    ::= { ocStbHostDevInterfaceTypes 15 }

ocStbHostHdmiIn OBJECT-IDENTITY
    STATUS      current
    DESCRIPTION
            "The type identifier used for HDMI input."
    ::= { ocStbHostDevInterfaceTypes 16 }

ocStbHostHdmiOut OBJECT-IDENTITY
    STATUS      current
    DESCRIPTION
            "The type identifier used for HDMI output."
    ::= { ocStbHostDevInterfaceTypes 17 }

ocStbHostRcaSpdifIn OBJECT-IDENTITY
    STATUS      current
    DESCRIPTION
            "The type identifier used for RCA SPDIF input."
    ::= { ocStbHostDevInterfaceTypes 18 }

ocStbHostRcaSpdifOut OBJECT-IDENTITY
    STATUS      current
    DESCRIPTION
            "The type identifier used for RCA SPDIF output."
    ::= { ocStbHostDevInterfaceTypes 19 }

ocStbHostToslinkSpdifIn OBJECT-IDENTITY
    STATUS      current
    DESCRIPTION
            "The type identifier used for Toslink SPDIF input."
    ::= { ocStbHostDevInterfaceTypes 20 }

ocStbHostToslinkSpdifOut OBJECT-IDENTITY
    STATUS      current
    DESCRIPTION
            "The type identifier used for Toslink SPDIF output."
    ::= { ocStbHostDevInterfaceTypes 21 }

ocStbHostDisplayOut OBJECT-IDENTITY
    STATUS      current
    DESCRIPTION
            "The type identifier used for the television
            screen output."
    ::= { ocStbHostDevInterfaceTypes 22 }

ocStbHost1394In OBJECT-IDENTITY
    STATUS      current
    DESCRIPTION
            "The type identifier used for IEEE-1394 input."
    ::= { ocStbHostDevInterfaceTypes 23 }

ocStbHost1394Out OBJECT-IDENTITY
    STATUS      current
    DESCRIPTION
            "The type identifier used for IEEE-1394 output."
    ::= { ocStbHostDevInterfaceTypes 24 }

ocStbHostDRIInterface OBJECT-IDENTITY
    STATUS      current
    DESCRIPTION
            "The type identifier used for the DRI interface."
    ::= { ocStbHostDevInterfaceTypes 25 }

-- A/V Interface Table

ocStbHostAVInterfaceTable OBJECT-TYPE
    SYNTAX      SEQUENCE OF OcStbHostAVInterfaceEntry
    MAX-ACCESS not-accessible
    STATUS      current
    DESCRIPTION
            "This table contains a list of A/V (Audio/Video)
            interfaces (video inputs/outputs, tuners, audio
            inputs/outputs) in the ocStbHost."
    ::= { ocStbHostInterfaces 2 }

ocStbHostAVInterfaceEntry OBJECT-TYPE
    SYNTAX      OcStbHostAVInterfaceEntry
     MAX-ACCESS not-accessible
     STATUS      current
     DESCRIPTION
             "Each entry describes the type and status of the A/V
             interface on the ocStbHost. The details of A/V interface
             entries may be defined in table extensions as indicated
             in the MIB object ocStbHostAVInterfaceType."
     INDEX { ocStbHostAVInterfaceIndex }
     ::= { ocStbHostAVInterfaceTable 1 }

OcStbHostAVInterfaceEntry ::=
    SEQUENCE {
        ocStbHostAVInterfaceIndex
            Unsigned32,
        ocStbHostAVInterfaceType
            AutonomousType,
        ocStbHostAVInterfaceDesc
            SnmpAdminString,
        ocStbHostAVInterfaceStatus
            INTEGER
     }

ocStbHostAVInterfaceIndex OBJECT-TYPE
    SYNTAX      Unsigned32 (1..4294967295)
    MAX-ACCESS not-accessible
    STATUS      current
    DESCRIPTION
            "Index of the table."
    ::= { ocStbHostAVInterfaceEntry 1 }

ocStbHostAVInterfaceType OBJECT-TYPE
    SYNTAX      AutonomousType
    MAX-ACCESS read-only
    STATUS      current
    DESCRIPTION
            "An indication of the type of interface.

            If this value is
               ocStbHostComponentOut
            then a corresponding entry exists in the
            ocStbHostComponentVideoTable.

            If this value is
               ocStbHostRFOutCh
            then a corresponding entry exists in the
            ocStbHostRFChannelOutTable.

            If this value is
               ocStbHostScte40FatRx
            then a corresponding entry exists in the
            ocStbHostInBandTunerTable.

            If this value is
               ocStbHostDviOut or ocStbHostHdmiOut
            then a corresponding entry exists in the
            ocStbHostDVIHDMITable

            If this value is
               ocStbHost1394Out
            then a corresponding entry exists in the
            ocStbHostIEEE1394Table

             If this value is
                hrDeviceOther
             then no further information is available for the device."
     ::= { ocStbHostAVInterfaceEntry 2 }

ocStbHostAVInterfaceDesc OBJECT-TYPE
    SYNTAX      SnmpAdminString
    MAX-ACCESS read-only
    STATUS      current
    DESCRIPTION
            "Textual description of the A/V Interface "
    ::= { ocStbHostAVInterfaceEntry 3 }

ocStbHostAVInterfaceStatus OBJECT-TYPE
    SYNTAX      INTEGER
                {
                enabled(1),
                disabled(2)
                }
    MAX-ACCESS read-only
    STATUS      current
    DESCRIPTION
            "Status of the interface.
            'enabled' indicates the A/V interface is active and can be
            used for the user.
            'disabled' indicates the A/V interface is currently not
            available for the user due to hardware, software or
            configuration conditions.
            Additional information about the interface status may be
            available in the A/V Type interface Table extensions."
    ::= { ocStbHostAVInterfaceEntry 4 }

--
--   IEEE 1394 Objects
--

ocStbHostIEEE1394Objects OBJECT IDENTIFIER ::= { ocStbHostInterfaces 3 }

ocStbHostIEEE1394Table OBJECT-TYPE
    SYNTAX      SEQUENCE OF OcStbHostIEEE1394Entry
    MAX-ACCESS not-accessible
    STATUS      current
    DESCRIPTION
            "This table contains attributes associated with the
            ocStbHost Interfaces of type IEEE 1394."
    ::= { ocStbHostIEEE1394Objects 1 }

ocStbHostIEEE1394Entry OBJECT-TYPE
    SYNTAX      OcStbHostIEEE1394Entry
    MAX-ACCESS not-accessible
    STATUS      current
    DESCRIPTION
            "An entry exists in this table for each
            interface of the type IEEE 1394."
    INDEX { ocStbHostAVInterfaceIndex }
    ::= { ocStbHostIEEE1394Table 1 }

OcStbHostIEEE1394Entry ::=
    SEQUENCE {
        ocStbHostIEEE1394ActiveNodes           Integer32,
        ocStbHostIEEE1394DataXMission          TruthValue,
        ocStbHostIEEE1394DTCPStatus            TruthValue,
        ocStbHostIEEE1394LoopStatus            TruthValue,
        ocStbHostIEEE1394RootStatus            TruthValue,
        ocStbHostIEEE1394CycleIsMaster         TruthValue,
        ocStbHostIEEE1394IRMStatus             TruthValue,
        ocStbHostIEEE1394AudioMuteStatus       TruthValue,
        ocStbHostIEEE1394VideoMuteStatus       TruthValue
        }

ocStbHostIEEE1394ActiveNodes OBJECT-TYPE
    SYNTAX      Integer32 (-1 | 0..64)
     UNITS       "nodes"
     MAX-ACCESS read-only
     STATUS      current
     DESCRIPTION
             "This object allows the manager to retrieve the
             number of nodes connected to the 1394 bus of
             the ocStbHost.
             The value '-1' means unknown number of nodes."
     ::= { ocStbHostIEEE1394Entry 1 }

ocStbHostIEEE1394DataXMission OBJECT-TYPE
    SYNTAX      TruthValue
    MAX-ACCESS read-only
    STATUS      current
    DESCRIPTION
            "This object allows the manager to retrieve the
            state of data being transmitted over the 1394
            bus. True indicates that data is being transmitted
            over the 1394 bus."
    ::= { ocStbHostIEEE1394Entry 2 }

ocStbHostIEEE1394DTCPStatus OBJECT-TYPE
    SYNTAX      TruthValue
    MAX-ACCESS read-only
    STATUS      current
    DESCRIPTION
            "This object allows the manager to retrieve the
            state of DTCP on the device. True indicates
            that DTCP is enabled and content is being encrypted
            of the 1394 link on the ocStbHost."
    ::= { ocStbHostIEEE1394Entry 3 }

ocStbHostIEEE1394LoopStatus OBJECT-TYPE
    SYNTAX      TruthValue
    MAX-ACCESS read-only
    STATUS      current
    DESCRIPTION
            "This object allows the manager to retrieve the
            state of a Loop present on the 1394 bus. True
            indicates that a Loop is present on the 1394 bus."
    ::= { ocStbHostIEEE1394Entry 4 }

ocStbHostIEEE1394RootStatus OBJECT-TYPE
    SYNTAX      TruthValue
    MAX-ACCESS read-only
    STATUS      current
    DESCRIPTION
            "This object allows the manager to retrieve the
            state of Root Status on the device. True indicates
            that the set-top is the Root node on the 1394 bus."
    ::= { ocStbHostIEEE1394Entry 5 }

ocStbHostIEEE1394CycleIsMaster OBJECT-TYPE
    SYNTAX      TruthValue
    MAX-ACCESS read-only
    STATUS      current
    DESCRIPTION
            "This object allows the manager to retrieve the
            state of Cycle Master on the device. True indicates
            that the set-top is Cycle Master on the 1394 bus."
    ::= { ocStbHostIEEE1394Entry 6 }

ocStbHostIEEE1394IRMStatus OBJECT-TYPE
    SYNTAX      TruthValue
    MAX-ACCESS read-only
    STATUS      current
    DESCRIPTION
            "This object allows the manager to retrieve the
            state of Isochronous Resource Master on the
            device. True indicates that the set-top is IRM
            on the 1394 bus."
    ::= { ocStbHostIEEE1394Entry 7 }

ocStbHostIEEE1394AudioMuteStatus OBJECT-TYPE
    SYNTAX      TruthValue
    MAX-ACCESS read-only
    STATUS      current
    DESCRIPTION
            "The value 'true' indicates that the audio signal
            is muted for this Interface. 'false' means the audio
            is not muted."
    ::= { ocStbHostIEEE1394Entry 8 }

ocStbHostIEEE1394VideoMuteStatus OBJECT-TYPE
    SYNTAX      TruthValue
    MAX-ACCESS read-only
    STATUS      current
    DESCRIPTION
            "The value 'true' indicates that the video signal
            is muted for this Interface. 'false' means the video
            signal is not muted."
    ::= { ocStbHostIEEE1394Entry 9 }

ocStbHostIEEE1394ConnectedDevicesTable OBJECT-TYPE
    SYNTAX      SEQUENCE OF OcStbHostIEEE1394ConnectedDevicesEntry
    MAX-ACCESS not-accessible
    STATUS      current
    DESCRIPTION
            "This table contains A/D Source Selection attributes
            associated to devices connected to the ocStbHost
            Interfaces of type IEEE 1394."
    ::= { ocStbHostIEEE1394Objects 2 }

ocStbHostIEEE1394ConnectedDevicesEntry OBJECT-TYPE
    SYNTAX      OcStbHostIEEE1394ConnectedDevicesEntry
    MAX-ACCESS not-accessible
    STATUS      current
    DESCRIPTION
            "An entry exist in this table for each
            device connected to all Interfaces of
            the type IEEE 1394."
    INDEX { ocStbHostIEEE1394ConnectedDevicesIndex }
    ::= { ocStbHostIEEE1394ConnectedDevicesTable 1 }

OcStbHostIEEE1394ConnectedDevicesEntry ::=
    SEQUENCE {
            ocStbHostIEEE1394ConnectedDevicesIndex
             Unsigned32,
            ocStbHostIEEE1394ConnectedDevicesAVInterfaceIndex
             Unsigned32,
            ocStbHostIEEE1394ConnectedDevicesSubUnitType
             INTEGER,
            ocStbHostIEEE1394ConnectedDevicesEui64
             OCTET STRING,
            ocStbHostIEEE1394ConnectedDevicesADSourceSelectSupport
             TruthValue
             }

ocStbHostIEEE1394ConnectedDevicesIndex OBJECT-TYPE
    SYNTAX      Unsigned32(1..4294967295)
    MAX-ACCESS not-accessible
    STATUS      current
    DESCRIPTION
            "The unique identifier of the connected device entry."
     ::= { ocStbHostIEEE1394ConnectedDevicesEntry 1 }

ocStbHostIEEE1394ConnectedDevicesAVInterfaceIndex OBJECT-TYPE
    SYNTAX      Unsigned32(1..4294967295)
    MAX-ACCESS read-only
    STATUS      current
    DESCRIPTION
            "This object allows the manager to retrieve the
            index value associated with the IEEE1394
            instance of ocStbHostAVInterfaceIndex
            to which the device is physically connected."
    ::= { ocStbHostIEEE1394ConnectedDevicesEntry 2 }

ocStbHostIEEE1394ConnectedDevicesSubUnitType OBJECT-TYPE
    SYNTAX      INTEGER {
                monitor(0),
                audio(1),
                printer(2),
                disc(3),
                tape(4),
                tuner(5),
                ca(6),
                camera(7),
                reserved(8),
                panel(9),
                other(10)
                }
    MAX-ACCESS read-only
    STATUS      current
    DESCRIPTION
            "This object allows the manager to retrieve the
            Subunit Type associated with the device connected
            to the ocStbHost's IEEE1394 interface."
    ::= { ocStbHostIEEE1394ConnectedDevicesEntry 3 }

ocStbHostIEEE1394ConnectedDevicesEui64 OBJECT-TYPE
    SYNTAX      OCTET STRING (SIZE (8))
    MAX-ACCESS read-only
    STATUS      current
    DESCRIPTION
            "This object allows the manager to retrieve the
            64-bit Extended Unique Identifier (EUI-64)
            associated with the device connected
            to the ocStbHost's IEEE1394 interface."
    ::= { ocStbHostIEEE1394ConnectedDevicesEntry 4 }

ocStbHostIEEE1394ConnectedDevicesADSourceSelectSupport OBJECT-TYPE
    SYNTAX      TruthValue
    MAX-ACCESS read-only
    STATUS      current
    DESCRIPTION
            "This object allows the manager to retrieve the
            status of Analog/Digital Source Selection support
            associated with the device connected to the
            ocStbHost's IEEE1394 interface.
            'true' indicates that the device supports A/D
            source selection."
    ::= { ocStbHostIEEE1394ConnectedDevicesEntry 5 }

ocStbHostDigitalVideoOutput OBJECT IDENTIFIER ::= { ocStbHostInterfaces 4 }

ocStbHostDVIHDMITable OBJECT-TYPE
    SYNTAX      SEQUENCE OF OcStbHostDVIHDMIEntry
    MAX-ACCESS not-accessible
    STATUS      current
    DESCRIPTION
            "This table allows the manager to retrieve information
            about the DVI/HDMI port of the ocStbHost."
    ::= { ocStbHostDigitalVideoOutput 1 }

ocStbHostDVIHDMIEntry OBJECT-TYPE
    SYNTAX      OcStbHostDVIHDMIEntry
    MAX-ACCESS not-accessible
    STATUS      current
    DESCRIPTION
            "An entry exists for each A/V interface of type HDMI or DVI
            of the ocStbHost."
    INDEX { ocStbHostAVInterfaceIndex }
    ::= { ocStbHostDVIHDMITable 1 }

OcStbHostDVIHDMIEntry ::=
    SEQUENCE {
        ocStbHostDVIHDMIOutputType
            INTEGER,
        ocStbHostDVIHDMIConnectionStatus
            TruthValue,
        ocStbHostDVIHDMIRepeaterStatus
            TruthValue,
        ocStbHostDVIHDMIVideoXmissionStatus
            TruthValue,
        ocStbHostDVIHDMIHDCPStatus
            TruthValue,
        ocStbHostDVIHDMIVideoMuteStatus
            TruthValue,
        ocStbHostDVIHDMIOutputFormat
            VideoOutputFormat,
        ocStbHostDVIHDMIAspectRatio
            VideoAspectRatio,
        ocStbHostDVIHDMIHostDeviceHDCPStatus
            INTEGER,
        ocStbHostDVIHDMIAudioFormat
            AudioOutputFormat,
        ocStbHostDVIHDMIAudioSampleRate
            INTEGER,
        ocStbHostDVIHDMIAudioChannelCount
            Unsigned32,
        ocStbHostDVIHDMIAudioMuteStatus
            TruthValue,
        ocStbHostDVIHDMIAudioSampleSize
            INTEGER,
        ocStbHostDVIHDMIColorSpace
            INTEGER,
        ocStbHostDVIHDMIFrameRate
            INTEGER,
        ocStbHostDVIHDMIAttachedDeviceType
            INTEGER,
        ocStbHostDVIHDMIEdid
            OCTET STRING,
        ocStbHostDVIHDMILipSyncDelay
            Integer32,
        ocStbHostDVIHDMICecFeatures
            BITS,
        ocStbHostDVIHDMIFeatures
            BITS,
        ocStbHostDVIHDMIMaxDeviceCount
            Integer32,
        ocStbHostDVIHDMIPreferredVideoFormat
            INTEGER,
        ocStbHostDVIHDMIEdidVersion
            SnmpAdminString,
        ocStbHostDVIHDMI3DCompatibilityControl
            INTEGER,
        ocStbHostDVIHDMI3DCompatibilityMsgDisplay
            TruthValue
     }

ocStbHostDVIHDMIOutputType OBJECT-TYPE
    SYNTAX      INTEGER
                {
                dvi(1),
                hdmi(2)
                }
    MAX-ACCESS read-only
    STATUS      current
    DESCRIPTION
            "This object defines the operational mode of the
            interface, where valid modes are dependent on
            the physical interface defined.

            If ocStbHostAVInterfaceIndex is DVI, then
            this value is always set to 1 (DVI).

             If ocStbHostAVInterfaceIndex is HDMI, then
             this value is either 1 (DVI) or 2 (HDMI)."
     ::= { ocStbHostDVIHDMIEntry 2 }

ocStbHostDVIHDMIConnectionStatus OBJECT-TYPE
    SYNTAX      TruthValue
    MAX-ACCESS read-only
    STATUS      current
    DESCRIPTION
            "This object allows the manager to retrieve the
            state of the DVI/HDMI port on the device.
            'true' indicates that a device is connected to
            the ocStbHost."
    ::= { ocStbHostDVIHDMIEntry 3 }

ocStbHostDVIHDMIRepeaterStatus OBJECT-TYPE
    SYNTAX      TruthValue
    MAX-ACCESS read-only
    STATUS      current
    DESCRIPTION
            "This object allows the manager to retrieve the
            presence of a repeater connected to the ocStbHost.
            'true' indicates that a repeater is connected
            to the ocStbHost."
    ::= { ocStbHostDVIHDMIEntry 4 }

ocStbHostDVIHDMIVideoXmissionStatus OBJECT-TYPE
    SYNTAX      TruthValue
    MAX-ACCESS read-only
    STATUS      current
    DESCRIPTION
            "This object allows the manager to retrieve the
            state of video transmission over the DVI/HDMI port
            of the ocStbHost. 'true' indicates that video is being
            transmitted over the DVI/HDMI link to a connected
            device."
    ::= { ocStbHostDVIHDMIEntry 5 }

ocStbHostDVIHDMIHDCPStatus OBJECT-TYPE
    SYNTAX      TruthValue
    MAX-ACCESS read-only
    STATUS      current
    DESCRIPTION
            "This object allows the manager to retrieve the
            state of the digital copy protection protocol in the
            interface.
            'true' indicates that HDCP encryption is enabled."
    ::= { ocStbHostDVIHDMIEntry 6 }

ocStbHostDVIHDMIVideoMuteStatus OBJECT-TYPE
    SYNTAX      TruthValue
    MAX-ACCESS read-only
    STATUS      current
    DESCRIPTION
            "The value 'true' indicates that the video signal
            is being muted over the DVI/HDMI link. 'false' means
            the video signal is not muted."
    ::= { ocStbHostDVIHDMIEntry 7 }

ocStbHostDVIHDMIOutputFormat OBJECT-TYPE
    SYNTAX      VideoOutputFormat
    MAX-ACCESS read-only
    STATUS      current
    DESCRIPTION
            "This object allows the manager to retrieve the
            video timing format currently being transmitted
            over the DVI/HDMI link."
    ::= { ocStbHostDVIHDMIEntry 8 }

ocStbHostDVIHDMIAspectRatio OBJECT-TYPE
    SYNTAX      VideoAspectRatio
    MAX-ACCESS read-only
    STATUS      current
    DESCRIPTION
            "This object allows the manager to retrieve the
            aspect ratio applicable to the video timing
            format currently being transmitted over the
            DVI/HDMI link. e.g., 4/3 or 16/9."
    ::= { ocStbHostDVIHDMIEntry 9 }

ocStbHostDVIHDMIHostDeviceHDCPStatus OBJECT-TYPE
    SYNTAX      INTEGER
                {
                nonHDCPdevice(1),
                compliantHDCPdevice(2),
                revokedHDCPdevice(3)
                }
    MAX-ACCESS read-only
    STATUS      current
    DESCRIPTION
            "Connected device HDCP status."
    ::= { ocStbHostDVIHDMIEntry 10 }

ocStbHostDVIHDMIAudioFormat OBJECT-TYPE
    SYNTAX      AudioOutputFormat
    MAX-ACCESS read-only
    STATUS      current
    DESCRIPTION
            "This object allows the manager to retrieve the
            audio format being transmitted over the
            HDMI link. If this entry corresponds to a DVI interface,
            this object is not instantiated."
    ::= { ocStbHostDVIHDMIEntry 11 }

ocStbHostDVIHDMIAudioSampleRate OBJECT-TYPE
    SYNTAX      INTEGER
                {
                other(1),
                samplerate32kHz(2),
                samplerate44kHz(3),
                samplerate48kHz(4),
                samplerate88kHz(5),
                samplerate96kHz(6),
                samplerate176kHz(7),
                samplerate192kHz(8)
                }
     MAX-ACCESS read-only
     STATUS      current
     DESCRIPTION
             "This object allows the manager to retrieve the
             audio sample rate being transmitted over the
             HDMI link. If this entry corresponds to a DVI interface,
             this object is not instantiated."
     ::= { ocStbHostDVIHDMIEntry 12 }

ocStbHostDVIHDMIAudioChannelCount OBJECT-TYPE
    SYNTAX      Unsigned32 (0..10)
    UNITS       "channels"
    MAX-ACCESS read-only
    STATUS      current
    DESCRIPTION
            "This object allows the manager to retrieve the
            audio channel count being transmitted over the
            HDMI link. If this entry corresponds to a DVI interface,
            this object is not instantiated."
    ::= { ocStbHostDVIHDMIEntry 13 }

ocStbHostDVIHDMIAudioMuteStatus OBJECT-TYPE
    SYNTAX      TruthValue
    MAX-ACCESS read-only
    STATUS      current
    DESCRIPTION
            "The value 'true' indicates that the audio signal is muted
            over the DVI/HDMI link. 'false' means the audio is not
            muted. This object is not instantiated for entries of
            ocStbHostDVIHDMIOutputType 'dvi'."
    ::= { ocStbHostDVIHDMIEntry 14 }

ocStbHostDVIHDMIAudioSampleSize OBJECT-TYPE
    SYNTAX      INTEGER
                {
                notValid(0),
                sample16Bit(1),
                sample20Bit(2),
                sample24Bit(3)
                }
    MAX-ACCESS read-only
    STATUS      current
    DESCRIPTION
            "Non-zero values pertain only to PCM audio formats and
            indicate the PCM sample size. This object applies only
            to HDMI outputs."
    ::= { ocStbHostDVIHDMIEntry 15 }

ocStbHostDVIHDMIColorSpace OBJECT-TYPE
    SYNTAX      INTEGER
                {
                rgb(0),
                ycc422(1),
                ycc444(2)
                }
    MAX-ACCESS read-only
    STATUS      current
    DESCRIPTION
            "Color space for HDMI outputs only."
    ::= { ocStbHostDVIHDMIEntry 16 }

ocStbHostDVIHDMIFrameRate OBJECT-TYPE
    SYNTAX      INTEGER
                {
                frameRateCode1(1),
                frameRateCode2(2),
                frameRateCode3(3),
                  frameRateCode4(4),
                  frameRateCode5(5),
                  frameRateCode6(6)
                  }
    MAX-ACCESS    read-only
    STATUS        current
    DESCRIPTION
            "Frame rates for HDMI outputs as defined in CCIF spec:
                frameRateCode1 = 23.976 Hz
                frameRateCode2 = 24.0 Hz
                frameRateCode3 = 29.97 Hz
                frameRateCode4 = 30.0 Hz
                frameRateCode5 = 59.94 Hz
                frameRateCode6 = 60.0 Hz."
    ::= { ocStbHostDVIHDMIEntry 17 }

ocStbHostDVIHDMIAttachedDeviceType OBJECT-TYPE
    SYNTAX      INTEGER
                {
                tv(0),
                recordingDevice(1),
                tuner(3),
                playbackDevice(4),
                audioSystem(5),
                other(6)
                }
    MAX-ACCESS read-only
    STATUS      current
    DESCRIPTION
            "The HDMI defined types of devices derived defined
            in the DHMI specification version 1.3a."
    ::= { ocStbHostDVIHDMIEntry 18 }

ocStbHostDVIHDMIEdid OBJECT-TYPE
    SYNTAX      OCTET STRING
    MAX-ACCESS read-only
    STATUS      current
    DESCRIPTION
            "EDID blob for debugging. A 0x00
            should be returned if an EDID is
            not available."
    ::= { ocStbHostDVIHDMIEntry 19 }

ocStbHostDVIHDMILipSyncDelay OBJECT-TYPE
    SYNTAX Integer32
    MAX-ACCESS read-only
    STATUS current
    DESCRIPTION
            "Defines the amount of delay in milliseconds that is
            being applied to the audio delivered over the HDMI
            link. A value of zero indicates that either no delay
            is being applied or Lip Sync is not supported by the
            device."
    ::= { ocStbHostDVIHDMIEntry 20 }

ocStbHostDVIHDMICecFeatures OBJECT-TYPE
    SYNTAX      BITS
                {
                oneTouchPlay(0),
                systemStandby(1),
                oneTouchRecord(2),
                timerProgramming(3),
                deckControl(4),
                tunerControl(5),
                deviceMenuControl(6),
                remoteControlPassThrough(7),
                systemAudioControl(8),
                deviceOsdNameTransfer(9),
                devicePowerStatus(10),
                osdDisplay(11),
                routingControl(12),
                systemInformation(13),
                vendorSpecificCommands(14),
                audioRateControl(15)
                }
     MAX-ACCESS read-only
     STATUS     current
     DESCRIPTION
             "This object lists all of the CEC Features supported by the
             device. When the bit is set, the feature is supported."
     ::= { ocStbHostDVIHDMIEntry 21 }

ocStbHostDVIHDMIFeatures OBJECT-TYPE
    SYNTAX      BITS
                {
                deepColor(0),
                extendedColorGamut(1),
                oneBitAudio(2),
                lipSync(3),
                cec(4)
                }
    MAX-ACCESS read-only
    STATUS      current
    DESCRIPTION
            "This object lists all of the HDMI Features supported by
            the device. When the bit is set, the feature is supported."
    ::= { ocStbHostDVIHDMIEntry 22 }

ocStbHostDVIHDMIMaxDeviceCount OBJECT-TYPE
    SYNTAX      Integer32
    MAX-ACCESS read-only
    STATUS      current
    DESCRIPTION
            "Defines the maximum number of downstream devices
            that this device can support."
    ::= { ocStbHostDVIHDMIEntry 23 }

ocStbHostDVIHDMIPreferredVideoFormat OBJECT-TYPE
    SYNTAX      INTEGER (0..127)
    MAX-ACCESS read-only
    STATUS      current
    DESCRIPTION
            "This object allows the manager to retrieve the
            preferred video format of the sink device. The
            value is an integer representing the video timing
            format expressed as a CEA-861 Video Identification
            Code (VIC).

             If the Host is not able to determine the preferred
             video format, or there is no corresponding VIC,
             then the Host sets this value to zero. The Host also
             sets this value to zero if there is no EDID or
             active HDMI/DVI connection in place."
     ::= { ocStbHostDVIHDMIEntry 24 }

ocStbHostDVIHDMIEdidVersion OBJECT-TYPE
    SYNTAX      SnmpAdminString
    MAX-ACCESS read-only
    STATUS      current
    DESCRIPTION
            "EDID version reported in bytes 18 and 19 of the EDID
            itself. It is in version.release format. A value of 0.0
            should be returned if an EDID is not available."
    ::= { ocStbHostDVIHDMIEntry 25 }

ocStbHostDVIHDMI3DCompatibilityControl OBJECT-TYPE
    SYNTAX      INTEGER
                {
                other(0),
                passthru3D(1),
                block3D(2)
                }
    MAX-ACCESS read-write
    STATUS      current
    DESCRIPTION
            "Defines what action to take for a display device that
            has not reported support for the received S3D content.
            passthru3D(1) requires the content to be passed
            onto the display device. blocked3D(2) requires the STB
            to not pass the content to the display device."
    DEFVAL { 1 }
    ::= { ocStbHostDVIHDMIEntry 26 }

ocStbHostDVIHDMI3DCompatibilityMsgDisplay OBJECT-TYPE
    SYNTAX      TruthValue
    MAX-ACCESS read-write
    STATUS      current
    DESCRIPTION
            "True(1) requires the STB to generate and transmit a warning
            message when the following occurs: 1) the STB receives
            S3D content and 2) the display device has not reported support
            for that format. The message should indicate that an
            incompatibility may exist between the source format and the
            display device capabilities. The STB must not send a warning
            message in this scenario if this object is set to false(2)."
    DEFVAL { 1 }
    ::= { ocStbHostDVIHDMIEntry 27 }

ocStbHostDVIHDMIAvailableVideoFormatTable OBJECT-TYPE
    SYNTAX      SEQUENCE OF OcStbHostDVIHDMIAvailableVideoFormatEntry
    MAX-ACCESS not-accessible
    STATUS      current
    DESCRIPTION
            "This table allows the manager to retrieve a list
            of all of the video timing formats reported by the
            sink device as per the device's EDID."
    ::= { ocStbHostDigitalVideoOutput 2 }

ocStbHostDVIHDMIAvailableVideoFormatEntry OBJECT-TYPE
    SYNTAX      OcStbHostDVIHDMIAvailableVideoFormatEntry
    MAX-ACCESS not-accessible
    STATUS      current
    DESCRIPTION
            "Entry in the ocStbHostDVIHDMIAvailableVideoFormatTable."
    INDEX { ocStbHostDVIHDMIAvailableVideoFormatIndex }
    ::= { ocStbHostDVIHDMIAvailableVideoFormatTable 1 }

OcStbHostDVIHDMIAvailableVideoFormatEntry ::=
    SEQUENCE {
             ocStbHostDVIHDMIAvailableVideoFormatIndex
                    INTEGER,
             ocStbHostDVIHDMIAvailableVideoFormat
                    INTEGER,
             ocStbHostDVIHDMISupported3DStructures
                    BITS,
             ocStbHostDVIHDMIActive3DStructure
                    INTEGER
             }

ocStbHostDVIHDMIAvailableVideoFormatIndex OBJECT-TYPE
    SYNTAX      INTEGER (0..127)
     MAX-ACCESS not-accessible
     STATUS      current
     DESCRIPTION
             "Index in the ocStbHostDVIHDMIAvailableVideoFormatTable."
     ::= { ocStbHostDVIHDMIAvailableVideoFormatEntry 1 }

ocStbHostDVIHDMIAvailableVideoFormat OBJECT-TYPE
    SYNTAX      INTEGER (0..127)
    MAX-ACCESS read-only
    STATUS      current
    DESCRIPTION
            "This object allows the manager to retrieve the
            available video formats of the sink device. The
            value is an integer representing the video timing
            format expressed as a CEA-861 Video Identification
            Code (VIC).

             If the Host is not able to determine the available
             video formats, or there is no corresponding VIC,
             then the Host makes an entry with a value of zero.
             The Host also makes an entry with a value of zero
             if there is no active HDMI/DVI connection in place."
     ::= { ocStbHostDVIHDMIAvailableVideoFormatEntry 2 }

ocStbHostDVIHDMISupported3DStructures OBJECT-TYPE
    SYNTAX      BITS
                {
                framePacking(0),
                fieldAlternative(1),
                lineAlternative(2),
                sideBySideFull(3),
                leftPlusDepth(4),
                leftPlusDepthPlusGraphicsPlusGraphicsDepth(5),
                topAndBottom(6),
                sideBySideHalf(7),
                sideBySideHalfQuincunx(8)
                }
    MAX-ACCESS read-only
    STATUS      current
    DESCRIPTION
            "This object reports the 3D structures supported by
            the sink as reported in the EDID VSDB. The supported
             structures are specified in [HDMI] Appendix H."
    ::= { ocStbHostDVIHDMIAvailableVideoFormatEntry 3 }

ocStbHostDVIHDMIActive3DStructure OBJECT-TYPE
    SYNTAX      INTEGER {
                other(0),
                na(1),
                framePacking(2),
                fieldAlternative(3),
                lineAlternative(4),
                sideBySideFull(5),
                leftPlusDepth(6),
                leftPlusDepthPlusGraphicsPlusGraphicsDepth(7),
                topAndBottom(8),
                sideBySideHalf(9),
                sideBySideHalfQuincunx(10),
                noAdditionalHDMIInfo(17),
                no3DInformation(18),
                infoFrameNotAvailable(19)
                }
    MAX-ACCESS read-only
    STATUS      current
    DESCRIPTION
            "This object allows the manager to retrieve the
            contents of the HDMI Vendor Specific InfoFrame currently
             being transmitted by the source. The video signal
             corresponds to the row associated with sink's current
             'active' VIC. Only one row can reflect an active 3D format
             at any point in time. The remaining, 'inactive', rows in
             this table should report 'na(1)' for not applicable.

             This object must be updated whenever the current
             HDMI InfoFrame content differs from the last HDMI InfoFrame
             transmitted. All reported values are based on the
             HDMI InfoFrame packet contents defined in [HDMI].

             If 3D is currently being signaled, report the 3D structure
             identified in the InfoFrame.

             If an HDMI InfoFrame is being transmitted but no 3D structure
             is being signaled, use the HDMI_Video_format values in the
             HDMI Infoframe to report as follows:

             000 - 'noAdditionalHDMIInfo(17)'
             001 - 'no3DInformation(18)'

             If an HDMI InfoFrame is not being transmitted, report
             'infoFrameNotAvailable(19)'."

    ::= { ocStbHostDVIHDMIAvailableVideoFormatEntry 4 }

--
-- Analog Video Table Information
--

ocStbHostAnalogOutput OBJECT IDENTIFIER ::= { ocStbHostInterfaces 5 }

ocStbHostComponentVideoTable OBJECT-TYPE
    SYNTAX      SEQUENCE OF OcStbHostComponentVideoEntry
    MAX-ACCESS not-accessible
    STATUS      current
    DESCRIPTION
            "This table allows the manager to retrieve information
            about a Component Video interface of the ocStbHost."
    ::= { ocStbHostAnalogOutput 1 }

ocStbHostComponentVideoEntry OBJECT-TYPE
    SYNTAX      OcStbHostComponentVideoEntry
    MAX-ACCESS not-accessible
    STATUS      current
    DESCRIPTION
            "An entry for each interface of type
            'ocStbHostComponentOut'."
    INDEX { ocStbHostAVInterfaceIndex }
    ::= { ocStbHostComponentVideoTable 1 }

OcStbHostComponentVideoEntry ::=
    SEQUENCE {
        ocStbHostComponentVideoConstrainedStatus       TruthValue,
        ocStbHostComponentOutputFormat                 VideoOutputFormat,
        ocStbHostComponentAspectRatio                  VideoAspectRatio,
        ocStbHostComponentVideoMuteStatus              TruthValue
        }

ocStbHostComponentVideoConstrainedStatus OBJECT-TYPE
    SYNTAX      TruthValue
    MAX-ACCESS read-only
    STATUS      current
    DESCRIPTION
            "This object allows the manager to retrieve the
            state of Constrained Video Image on the port.
            True indicates that video is being constrained
             over the component video output port."
     ::= { ocStbHostComponentVideoEntry 1 }

ocStbHostComponentOutputFormat OBJECT-TYPE
    SYNTAX      VideoOutputFormat
    MAX-ACCESS read-only
    STATUS      current
    DESCRIPTION
            "This object allows the manager to retrieve the
            video format currently being transmitted over
            the Component Video output port."
    ::= { ocStbHostComponentVideoEntry 2 }

ocStbHostComponentAspectRatio OBJECT-TYPE
    SYNTAX      VideoAspectRatio
    MAX-ACCESS read-only
    STATUS      current
    DESCRIPTION
            "This object allows the manager to retrieve the
            video aspect ratio currently being transmitted over
            the Component Video output port."
    ::= { ocStbHostComponentVideoEntry 3 }

ocStbHostComponentVideoMuteStatus OBJECT-TYPE
    SYNTAX      TruthValue
    MAX-ACCESS read-only
    STATUS      current
    DESCRIPTION
            "The value 'true' indicates that the video signal is
            muted for this Interface. 'false' means the video
            signal is not muted."
    ::= { ocStbHostComponentVideoEntry 4 }

--
-- NTSC RF Output
--

ocStbHostRFChannelOutTable OBJECT-TYPE
    SYNTAX      SEQUENCE OF OcStbHostRFChannelOutEntry
    MAX-ACCESS not-accessible
    STATUS      current
    DESCRIPTION
            "This table allows the manager to retrieve information
            about an RF channel output interface of the ocStbHost."
    ::= { ocStbHostAnalogOutput 2 }

ocStbHostRFChannelOutEntry OBJECT-TYPE
    SYNTAX      OcStbHostRFChannelOutEntry
    MAX-ACCESS not-accessible
    STATUS      current
    DESCRIPTION
            "An entry for each interface of type 'ocStbHostRFOutCh'."
    INDEX { ocStbHostAVInterfaceIndex }
    ::= { ocStbHostRFChannelOutTable 1 }

OcStbHostRFChannelOutEntry ::=
    SEQUENCE {
        ocStbHostRFChannelOut                        Unsigned32,
        ocStbHostRFChannelOutAudioMuteStatus         TruthValue,
        ocStbHostRFChannelOutVideoMuteStatus         TruthValue
        }

ocStbHostRFChannelOut OBJECT-TYPE
    SYNTAX      Unsigned32 (3..99)
    MAX-ACCESS read-only
    STATUS      current
    DESCRIPTION
            "Indicates the RF channel out value. Typical values are
            3 or 4 for Channels 3 and 4, respectively."
    ::= { ocStbHostRFChannelOutEntry 2 }

ocStbHostRFChannelOutAudioMuteStatus OBJECT-TYPE
    SYNTAX      TruthValue
    MAX-ACCESS read-only
    STATUS      current
    DESCRIPTION
            "The value 'true' indicates that the audio signal is
            muted for this Interface. 'false' means the audio
            is not muted."
    ::= { ocStbHostRFChannelOutEntry 3 }

ocStbHostRFChannelOutVideoMuteStatus OBJECT-TYPE
    SYNTAX      TruthValue
    MAX-ACCESS read-only
    STATUS      current
    DESCRIPTION
            "The value 'true' indicates that the video signal is
            muted for this Interface. 'false' means the video
            signal is not muted."
    ::= { ocStbHostRFChannelOutEntry 4 }

--
-- Sony Philips Digital Audio Interface
--

ocStbHostSPDIfTable OBJECT-TYPE
    SYNTAX      SEQUENCE OF OcStbHostSPDIfEntry
    MAX-ACCESS not-accessible
    STATUS      current
    DESCRIPTION
            "This table allows the manager to retrieve information
            about the SONY, Philips Digital (SPD) Interface of the
            ocStbHost."
    ::= { ocStbHostInterfaces 6 }

ocStbHostSPDIfEntry OBJECT-TYPE
    SYNTAX      OcStbHostSPDIfEntry
    MAX-ACCESS not-accessible
    STATUS      current
    DESCRIPTION
            "An entry exists for each Audio interface of type SPD."
    INDEX { ocStbHostAVInterfaceIndex }
    ::= { ocStbHostSPDIfTable 1 }

OcStbHostSPDIfEntry ::= SEQUENCE {
        ocStbHostSPDIfAudioFormat             AudioOutputFormat,
        ocStbHostSPDIfAudioMuteStatus         TruthValue
        }

ocStbHostSPDIfAudioFormat OBJECT-TYPE
    SYNTAX      AudioOutputFormat
    MAX-ACCESS read-only
    STATUS      current
    DESCRIPTION
            "The format of the Audio stream transmitted over this
            interface."
    ::= { ocStbHostSPDIfEntry 1 }

ocStbHostSPDIfAudioMuteStatus OBJECT-TYPE
    SYNTAX      TruthValue
    MAX-ACCESS read-only
    STATUS      current
    DESCRIPTION
            "The value 'true' indicates that the audio signal is muted
             over the SPDIF link. 'false' means the audio is not muted."
     ::= { ocStbHostSPDIfEntry 2 }

ocStbHostServiceProgramInfo OBJECT IDENTIFIER ::= { ocStbHostInterfaces 7 }

ocStbHostInBandTunerTable OBJECT-TYPE
    SYNTAX      SEQUENCE OF OcStbHostInBandTunerEntry
    MAX-ACCESS not-accessible
    STATUS      current
    DESCRIPTION
            "This Object Table allows the manager to retrieve
            information regarding the In-Band tuner(s) in
            the ocStbHost."
    ::= { ocStbHostServiceProgramInfo 1 }

ocStbHostInBandTunerEntry OBJECT-TYPE
    SYNTAX      OcStbHostInBandTunerEntry
    MAX-ACCESS not-accessible
    STATUS      current
    DESCRIPTION
            "This entry contains information regarding
            a tuner of type ocStbHostScte40FatRx in the ocStbHost."
    INDEX { ocStbHostAVInterfaceIndex }
    ::= { ocStbHostInBandTunerTable 1 }

OcStbHostInBandTunerEntry ::=
    SEQUENCE {
        ocStbHostInBandTunerModulationMode
            INTEGER,
        ocStbHostInBandTunerFrequency
            Unsigned32,
        ocStbHostInBandTunerInterleaver
            INTEGER,
        ocStbHostInBandTunerPower
            TenthdBmV,
        ocStbHostInBandTunerAGCValue
            Unsigned32,
        ocStbHostInBandTunerSNRValue
            TenthdB,
        ocStbHostInBandTunerUnerroreds
            Counter32,
        ocStbHostInBandTunerCorrecteds
            Counter32,
        ocStbHostInBandTunerUncorrectables
            Counter32,
        ocStbHostInBandTunerCarrierLockLost
            Counter32,
        ocStbHostInBandTunerPCRErrors
            Counter32,
        ocStbHostInBandTunerPTSErrors
            Counter32,
        ocStbHostInBandTunerState
            INTEGER,
        ocStbHostInBandTunerBER
            INTEGER,
        ocStbHostInBandTunerSecsSinceLock
            Unsigned32,
        ocStbHostInBandTunerEqGain
            Integer32,
        ocStbHostInBandTunerMainTapCoeff
            INTEGER,
        ocStbHostInBandTunerTotalTuneCount
            Counter32,
        ocStbHostInBandTunerTuneFailureCount
            Counter32,
        ocStbHostInBandTunerTuneFailFreq
            Unsigned32,
          ocStbHostInBandTunerBandwidth
              INTEGER
          }

ocStbHostInBandTunerModulationMode OBJECT-TYPE
    SYNTAX      INTEGER
                {
                other(1),
                analog(2),
                qam64(3),
                qam256(4)
                }
    MAX-ACCESS read-only
    STATUS      current
    DESCRIPTION
            "The In-band tuner modulation mode.

            Modulation modes are as follows:
            other    - IB is configured in a manner not described
                       by any other listed mode.
            Analog   - IB is configured for analog service.
            QAM-64   - IB is configured for a digital service that
                       is 64-QAM.
            QAM-256 - IB is configured for a digital service that
                       is 256-QAM."
    ::= { ocStbHostInBandTunerEntry 1 }

ocStbHostInBandTunerFrequency OBJECT-TYPE
    SYNTAX      Unsigned32
    UNITS       "hertz"
    MAX-ACCESS read-only
    STATUS      current
    DESCRIPTION
            "This object allows the manager to retrieve the center
            frequency of the currently tuned channel in Hz."
    ::= { ocStbHostInBandTunerEntry 2 }

ocStbHostInBandTunerInterleaver OBJECT-TYPE
    SYNTAX      INTEGER {
                unknown(1),
                other(2),
                taps64Increment2(3),
                taps128Increment1(4),
                taps128increment2(5),
                taps128increment3(6),
                taps128increment4(7),
                taps32increment4(8),
                taps16increment8(9),
                taps8increment16(10)
                }
    MAX-ACCESS read-only
    STATUS      current
    DESCRIPTION
            "The in-band interface interleaver value.
               set to '3' current operational mode 'taps64Increment2'
               set to '4' current operational mode 'taps128Increment1'
               set to '5' current operational mode 'taps128increment2'
               set to '6' current operational mode 'taps128increment3'
               set to '7' current operational mode 'taps128increment4'
               set to '8' current operational mode 'taps32increment4'
               set to '9' current operational mode 'taps16increment8'
               set to '10' current operational mode 'taps8increment16'"
    ::= { ocStbHostInBandTunerEntry 3 }
ocStbHostInBandTunerPower OBJECT-TYPE
    SYNTAX      TenthdBmV
    UNITS       "dBmV"
    MAX-ACCESS read-only
     STATUS      current
     DESCRIPTION
             "The received power level of this in-band interface."
     ::= { ocStbHostInBandTunerEntry 4 }

ocStbHostInBandTunerAGCValue OBJECT-TYPE
    SYNTAX      Unsigned32(0..100)
    UNITS       "percentage"
    MAX-ACCESS read-only
    STATUS      current
    DESCRIPTION
            "This object allows the manager to retrieve the
            In-band channel AGC value (%). When an In-band
            Carrier Lock is indicated, a value of 0 (zero)
            indicates that the ocStbHost does not compute the
            value."
    ::= { ocStbHostInBandTunerEntry 5 }

ocStbHostInBandTunerSNRValue OBJECT-TYPE
    SYNTAX      TenthdB
    UNITS       "dB"
    MAX-ACCESS read-only
    STATUS      current
    DESCRIPTION
            "This object allows the manager to retrieve the
            In-band channel SNR value (1/10 dB). When an
            In-band Carrier Lock is indicated, a value of 0
            (zero) indicates that the ocStbHost does not compute
            the value."
    ::= { ocStbHostInBandTunerEntry 6 }

ocStbHostInBandTunerUnerroreds OBJECT-TYPE
    SYNTAX      Counter32
    UNITS       "codewords"
    MAX-ACCESS read-only
    STATUS      current
    DESCRIPTION
            "Codewords received on this channel without error.
            Discontinuities in the value of this counter can occur
            at reinitialization of the managed system, and at other
            times as indicated by the value of
            ifCounterDiscontinuityTime for the associated ifIndex."
    ::= { ocStbHostInBandTunerEntry 7 }

ocStbHostInBandTunerCorrecteds OBJECT-TYPE
    SYNTAX      Counter32
    UNITS       "codewords"
    MAX-ACCESS read-only
    STATUS      current
    DESCRIPTION
            "Codewords received on this in-band channel with
            correctable errors. Discontinuities in the value of
            this counter can occur at reinitialization of the
            managed system."
    ::= { ocStbHostInBandTunerEntry 8 }

ocStbHostInBandTunerUncorrectables OBJECT-TYPE
    SYNTAX      Counter32
    UNITS       "codewords"
    MAX-ACCESS read-only
    STATUS      current
    DESCRIPTION
            "Codewords received on this in-band channel with
            uncorrectable errors.
            Discontinuities in the value of this counter can occur
            at reinitialization of the managed system."
    ::= { ocStbHostInBandTunerEntry 9 }

ocStbHostInBandTunerCarrierLockLost OBJECT-TYPE
    SYNTAX      Counter32
    MAX-ACCESS read-only
    STATUS      current
    DESCRIPTION
            "The number of times the ocStbHost has detected carrier
            Lock is lost.
            Discontinuities in the value of this counter can occur
            at reinitialization of the managed system."
    ::= { ocStbHostInBandTunerEntry 10 }

ocStbHostInBandTunerPCRErrors OBJECT-TYPE
    SYNTAX      Counter32
    MAX-ACCESS read-only
    STATUS      current
    DESCRIPTION
            "The number of times the Program Clock Reference (PCR)
            detected Synchronization errors; e.g., wrong PCR from
            multiplexer, excessive CPR Jitter, etc.
            Discontinuities in the value of this counter can occur
            at reinitialization of the managed system."
    ::= { ocStbHostInBandTunerEntry 11 }

ocStbHostInBandTunerPTSErrors OBJECT-TYPE
    SYNTAX      Counter32
    MAX-ACCESS read-only
    STATUS      current
    DESCRIPTION
            "The number of Presentation TimeStamp (PTS) packets that
            encounter sequencing errors.
            Discontinuities in the value of this counter can occur
            at reinitialization of the managed system."
    ::= { ocStbHostInBandTunerEntry 12 }

ocStbHostInBandTunerState OBJECT-TYPE
    SYNTAX      INTEGER {
                ready(1),
                waitingSync(2),
                waitingQam(3),
                foundSync(4),
                foundQam(5),
                unknown(6),
                standby(7)
                }
    MAX-ACCESS read-only
    STATUS      current
    DESCRIPTION
            "The In-band tuner current state.

            Modulation modes are as follows:
            ready - indicates that the tuner is in idle mode (not
                currently in use).
            waitingSync - indicates that the tuner is trying to
                find sync on an analog channel.
            waitingQam - indicates that the tuner is trying to tune
                to the desired QAM frequency and lock onto valid data.
            foundSync - indicates that the tuner has successfully
                tuned to an analog channel.
            foundQam - indicates that the tuner has successfully
                tuned to a digital channel."
    ::= { ocStbHostInBandTunerEntry 13 }

ocStbHostInBandTunerBER OBJECT-TYPE
    SYNTAX      INTEGER
                {
                berGreaterThan10e2(1),
                berRange10e2ToGreaterThan10e4(2),
                berRange10e4ToGreaterThan10e6(3),
                berRange10e6ToGreaterThan10e8(4),
                berRange10e8ToGreaterThan10e12(5),
                berEqualToOrLessThan10e12(6),
                berNotApplicable(7)
                }
     MAX-ACCESS read-only
     STATUS     current
     DESCRIPTION
             "The average Bit Error Rate range since last tune to a digital
             channel. This value is determined by dividing the number of
             erroneous bits by the total number of bits transmitted
             within the last 10 minutes of the object being polled.
             Report value of 7 if tuned to an analog channel."
     ::= { ocStbHostInBandTunerEntry 14 }

ocStbHostInBandTunerSecsSinceLock OBJECT-TYPE
    SYNTAX      Unsigned32
    MAX-ACCESS read-only
    STATUS      current
    DESCRIPTION
            "The amount of time, in seconds, since the last tuner lock
            on a valid data signal. Each time the tuner locks the
            ocStbHostInBandTunerUnerroreds,
            ocStbHostInBandTunerCorrecteds, and
            ocStbHostInBandTunerUncorrectables, counters should be
            set to 0."
    ::= { ocStbHostInBandTunerEntry 15 }

ocStbHostInBandTunerEqGain OBJECT-TYPE
    SYNTAX      Integer32
    MAX-ACCESS read-only
    STATUS      current
    DESCRIPTION
            "The value of the equalizer gain on the QAM data channel.
             A value of 0 (zero) indicates that the ocStbHost does not
             compute the value."
    ::= { ocStbHostInBandTunerEntry 16 }

ocStbHostInBandTunerMainTapCoeff OBJECT-TYPE
    SYNTAX      INTEGER(1..32767)
    MAX-ACCESS read-only
    STATUS      current
    DESCRIPTION
            "The normalized main tap coefficient used for calibrating
            data path delay or frequency response. A value of 0 (zero)
            indicates that the ocStbHost does not compute the value."
    ::= { ocStbHostInBandTunerEntry 17 }

ocStbHostInBandTunerTotalTuneCount OBJECT-TYPE
    SYNTAX      Counter32
    MAX-ACCESS read-only
    STATUS      current
    DESCRIPTION
            "The number of times an attempt has been made to change
            the tuned frequency. This includes both successful and
            unsuccessful attempts."
    ::= { ocStbHostInBandTunerEntry 18 }

ocStbHostInBandTunerTuneFailureCount OBJECT-TYPE
    SYNTAX      Counter32
    MAX-ACCESS read-only
    STATUS      current
    DESCRIPTION
            "The number of times an attempt to change the tuned
            frequency has resulted in a failure to acquire a signal
            (either analog or digital)."
    ::= { ocStbHostInBandTunerEntry 19 }

ocStbHostInBandTunerTuneFailFreq OBJECT-TYPE
    SYNTAX      Unsigned32
    UNITS       "hertz"
    MAX-ACCESS read-only
    STATUS      current
    DESCRIPTION
            "The most recent frequency at which an attempt to tune
            resulted in an increment of
            ocStbHostInBandTunerTuneFailureCount. If no tune attempt
            has failed since initialization, this value
            SHALL be zero."
    ::= { ocStbHostInBandTunerEntry 20 }

ocStbHostInBandTunerBandwidth OBJECT-TYPE
    SYNTAX      INTEGER
                {
                other(1),
                mHz864(2),
                mHz1002(3)
                }
    MAX-ACCESS read-only
    STATUS      current
    DESCRIPTION
            "The In-band tuner bandwidth.
            Tuner bandwidth choices are as follows:
            other     - Tuning range is not described
                        by any other listed range.
            mHz864    - Tuning range is 54 to 864 MHz
            mHz1002   - Tuning range is 54 to 1002 MHz."
    ::= { ocStbHostInBandTunerEntry 21 }

ocStbHostProgramStatusTable OBJECT-TYPE
    SYNTAX      SEQUENCE OF OcStbHostProgramStatusEntry
    MAX-ACCESS not-accessible
    STATUS      current
    DESCRIPTION
            "A table of current program content being forwarded by the
            ocStbHost."
    ::= { ocStbHostServiceProgramInfo 2 }

ocStbHostProgramStatusEntry OBJECT-TYPE
    SYNTAX      OcStbHostProgramStatusEntry
    MAX-ACCESS not-accessible
    STATUS      current
    DESCRIPTION
            "There is an entry in this table for each active program
            content path.
            This means that the same program content source and/or
            destination can be associated to multiple A/V interface
            combinations as different entries in this table."
    INDEX { ocStbHostProgramIndex }
    ::= { ocStbHostProgramStatusTable 1 }

OcStbHostProgramStatusEntry ::=
    SEQUENCE {
        ocStbHostProgramIndex
            Unsigned32,
        ocStbHostProgramAVSource
            RowPointer,
        ocStbHostProgramAVDestination
            RowPointer,
        ocStbHostProgramContentSource
            RowPointer,
        ocStbHostProgramContentDestination
           RowPointer
       }

ocStbHostProgramIndex OBJECT-TYPE
    SYNTAX      Unsigned32 (1..20)
    MAX-ACCESS not-accessible
    STATUS      current
    DESCRIPTION
            "Index for Program Status Entry Table."
    ::= { ocStbHostProgramStatusEntry 1 }

ocStbHostProgramAVSource OBJECT-TYPE
    SYNTAX      RowPointer
    MAX-ACCESS read-only
    STATUS      current
    DESCRIPTION
            "Defines the source interface
            associated with this entry. Example sources are
            interfaces listed in the ifTable, interfaces listed in
            ocStbAVInterfaceTable, or a Host Resources Device such as a
            DVR.
            If the source corresponds to an entry in the
            ocStbAVInterfaceTable, this object reports the
            ocStbAVInterfaceType instance of the source interface.
            If the source corresponds to a resource listed in the
            ifTable, this object reports the ifIndex instance of
            the source interface.
            If the source corresponds to a resource listed in
            hrDeviceTable, this object reports the hrDeviceType
            instance of the source interface.
            Other table rows may be designated by this object
            as appropriate to the particular source."
    ::= { ocStbHostProgramStatusEntry 2 }

ocStbHostProgramAVDestination OBJECT-TYPE
    SYNTAX      RowPointer
    MAX-ACCESS read-only
    STATUS      current
    DESCRIPTION
            "Defines the destination interface
            associated with this entry. Example destinations are
            interfaces listed in the ifTable, interfaces listed in
            ocStbAVInterfaceTable,
            or a Host Resource Device such as a DVR.
            If the destination corresponds to an entry in the
            ocStbAVInterfaceTable, this object reports the
            ocStbAVInterfaceType instance of the destination
            interface.
            If the destination corresponds to an interface listed in
            the ifTable, this object reports the ifIndex instance of
            the destination interface.
            If the destination corresponds to a resource listed in the
            hrDeviceTable, this object reports the hrDeviceType
            instance of the destination interface.
            Other table rows may be designated by this object
            as appropriate to the particular destination."
    ::= { ocStbHostProgramStatusEntry 3 }

ocStbHostProgramContentSource OBJECT-TYPE
    SYNTAX      RowPointer
    MAX-ACCESS read-only
    STATUS      current
    DESCRIPTION
            "A pointer to the first visible object structure that
            defines the type of content associated to the A/V source
            interface. If the content is from an MPEG2 stream, this
            object points to the first visible object in
            ocStbHostMpeg2ContentEntry.
            Vendor-specific Content models may be defined in the vendor
            enterprise IANA assigned OID.
            This object reports 'zeroDotZero' value if no content
            information is available."
    ::= { ocStbHostProgramStatusEntry 4 }

ocStbHostProgramContentDestination OBJECT-TYPE
    SYNTAX      RowPointer
    MAX-ACCESS read-only
    STATUS      current
    DESCRIPTION
            "A pointer to the first visible object structure that
            defines the type of content associated to the A/V
            destination interface. For example, if the content for the
            destination interface is an MPEG2 stream
            (e.g., IEEE 1394 SPTS), this object points to the
            first visible object in ocStbHostMpeg2ContentEntry.
            Vendor-specific Content models may be defined in the vendor
            enterprise IANA assigned OID.
            This object reports 'zeroDotZero' value if no content
            information is available."
    ::= { ocStbHostProgramStatusEntry 5 }

--
-- MPEG2 Streaming Content Information
--

ocStbHostMpeg2ContentTable OBJECT-TYPE
    SYNTAX      SEQUENCE OF OcStbHostMpeg2ContentEntry
    MAX-ACCESS not-accessible
    STATUS      current
    DESCRIPTION
            "Contains information associated to an MPEG-2
            Program carried by an MPEG-2 transport stream.
            Entries in this table can be
            associated to interfaces receiving or forwarding
            MPEG-2 content."
    ::= { ocStbHostServiceProgramInfo 3 }

ocStbHostMpeg2ContentEntry OBJECT-TYPE
    SYNTAX      OcStbHostMpeg2ContentEntry
    MAX-ACCESS not-accessible
    STATUS      current
    DESCRIPTION
            "The conceptual row for this table."
    INDEX { ocStbHostMpeg2ContentIndex }
    ::= { ocStbHostMpeg2ContentTable 1 }

OcStbHostMpeg2ContentEntry::=
    SEQUENCE {
        ocStbHostMpeg2ContentIndex
            Unsigned32,
        ocStbHostMpeg2ContentProgramNumber
            Unsigned32,
        ocStbHostMpeg2ContentTransportStreamID
            Unsigned32,
        ocStbHostMpeg2ContentTotalStreams
            Unsigned32,
        ocStbHostMpeg2ContentSelectedVideoPID
            Integer32,
        ocStbHostMpeg2ContentSelectedAudioPID
            Integer32,
        ocStbHostMpeg2ContentOtherAudioPIDs
            TruthValue,
        ocStbHostMpeg2ContentCCIValue
            INTEGER,
       ocStbHostMpeg2ContentAPSValue
           INTEGER,
       ocStbHostMpeg2ContentCITStatus
           TruthValue,
       ocStbHostMpeg2ContentBroadcastFlagStatus
           TruthValue,
       ocStbHostMpeg2ContentEPNStatus
           TruthValue,
       ocStbHostMpeg2ContentPCRPID
           Integer32,
       ocStbHostMpeg2ContentPCRLockStatus
           INTEGER,
       ocStbHostMpeg2ContentDecoderPTS
           Integer32,
       ocStbHostMpeg2ContentDiscontinuities
           Counter32,
       ocStbHostMpeg2ContentPktErrors
           Counter32,
       ocStbHostMpeg2ContentPipelineErrors
           Counter32,
       ocStbHostMpeg2ContentDecoderRestarts
           Counter32
       }

ocStbHostMpeg2ContentIndex OBJECT-TYPE
    SYNTAX      Unsigned32 (1..20)
    MAX-ACCESS not-accessible
    STATUS      current
    DESCRIPTION
            "The unique identifier for the Mpeg2 Content entries in
            this table."
    ::= { ocStbHostMpeg2ContentEntry 1 }

ocStbHostMpeg2ContentProgramNumber OBJECT-TYPE
    SYNTAX      Unsigned32
    MAX-ACCESS read-only
    STATUS      current
    DESCRIPTION
            "The program Number associated with active content within
            the ocStbHost."
    ::= { ocStbHostMpeg2ContentEntry 2 }

ocStbHostMpeg2ContentTransportStreamID OBJECT-TYPE
    SYNTAX      Unsigned32
    MAX-ACCESS read-only
    STATUS      current
    DESCRIPTION
            "Defines the transport stream ID associated with the
            program number."
    ::= { ocStbHostMpeg2ContentEntry 3 }

ocStbHostMpeg2ContentTotalStreams OBJECT-TYPE
    SYNTAX      Unsigned32
    UNITS       "streams"
    MAX-ACCESS read-only
    STATUS      current
    DESCRIPTION
            "Defines the total number of elementary streams associated
            with the program number."
    ::= { ocStbHostMpeg2ContentEntry 4 }

ocStbHostMpeg2ContentSelectedVideoPID OBJECT-TYPE
    SYNTAX      Integer32 (-1 | 1..8191)
    MAX-ACCESS read-only
    STATUS      current
    DESCRIPTION
            "This object allows the manager to retrieve the
            PID associated to the selected video
            stream. The value '-1' indicates that no video stream
            is being selected or identified.
            The value is the 13-bit PID value expressed in decimal."
    ::= { ocStbHostMpeg2ContentEntry 5 }

ocStbHostMpeg2ContentSelectedAudioPID OBJECT-TYPE
    SYNTAX      Integer32 (-1 | 1..8191)
    MAX-ACCESS read-only
    STATUS      current
    DESCRIPTION
            "The selected audio PID.
            The value '-1' indicates no audio stream identified."
    ::= { ocStbHostMpeg2ContentEntry 6 }

ocStbHostMpeg2ContentOtherAudioPIDs OBJECT-TYPE
    SYNTAX      TruthValue
    MAX-ACCESS read-only
    STATUS      current
    DESCRIPTION
            "Then value 'true' indicates the MPEG-2 program
            has more than one audio PID.
            'false' indicates the MPEG-2 program has only one
            audio PID."
    ::= { ocStbHostMpeg2ContentEntry 7 }

ocStbHostMpeg2ContentCCIValue OBJECT-TYPE
    SYNTAX      INTEGER
                {
                copyFreely(0),
                copyNoMore(1),
                copyOneGeneration(2),
                copyNever(3),
                undefined(4)
                }
    MAX-ACCESS read-only
    STATUS      current
    DESCRIPTION
            "This value allows the manager to retrieve the
            encryption Mode Indication (EMI) Bits of the
            Copy Control Information (CCI) byte associated
            with the service."
    ::= { ocStbHostMpeg2ContentEntry 8 }

ocStbHostMpeg2ContentAPSValue OBJECT-TYPE
    SYNTAX      INTEGER
                {
                type1(1),
                type2(2),
                type3(3),
                noMacrovision(4),
                notDefined(5)
                }
    MAX-ACCESS read-only
    STATUS      current
    DESCRIPTION
            "This value allows the manager to retrieve the
            Analog Protection System (APS) bits of the
            Copy Control Information (CCI) byte
            associated with the service.
            'type1' indicates AGC ON, split burst OFF
            'type2' indicates AGC ON, 2-line split burst
            'type3' indicates AGC ON, 4-line split burst."
    ::= { ocStbHostMpeg2ContentEntry 9 }

ocStbHostMpeg2ContentCITStatus OBJECT-TYPE
    SYNTAX      TruthValue
     MAX-ACCESS read-only
     STATUS      current
     DESCRIPTION
             "This value allows the manager to retrieve the state
             of the Constrained Image Trigger(CIT).

             'true' indicates image constraint required.
             'false' indicates image constraint not asserted."
     ::= { ocStbHostMpeg2ContentEntry 10 }

ocStbHostMpeg2ContentBroadcastFlagStatus OBJECT-TYPE
    SYNTAX      TruthValue
    MAX-ACCESS read-only
    STATUS      current
    DESCRIPTION
            "This value allows the manager to retrieve the state
            of Broadcast Flag in the source interface.
            'true' indicates Broadcast Flag present.
            'false' indicates Broadcast Flag not present."
    ::= { ocStbHostMpeg2ContentEntry 11 }

ocStbHostMpeg2ContentEPNStatus OBJECT-TYPE
    SYNTAX      TruthValue
    MAX-ACCESS read-only
    STATUS      current
    DESCRIPTION
            "This object allows the manager to retrieve the
            EPN status of the MPEG stream. 'true' indicates
            that EPN is asserted."
    ::= { ocStbHostMpeg2ContentEntry 12 }

ocStbHostMpeg2ContentPCRPID OBJECT-TYPE
    SYNTAX      Integer32 (-1 | 1..8191)
    MAX-ACCESS read-only
    STATUS      current
    DESCRIPTION
            "This object allows the manager to retrieve the
            PCR PID associated to the selected video
            stream. The value '-1' indicates that no video stream
            is being selected or identified. The value is the 13-bit
            PCR PID value expressed in decimal."
    ::= { ocStbHostMpeg2ContentEntry 13 }

ocStbHostMpeg2ContentPCRLockStatus OBJECT-TYPE
    SYNTAX      INTEGER
                {
                notLocked(1),
                locked(2)
                }
    MAX-ACCESS read-only
    STATUS      current
    DESCRIPTION
            "The status of the Program Clock Reference lock."
    ::= { ocStbHostMpeg2ContentEntry 14 }

ocStbHostMpeg2ContentDecoderPTS OBJECT-TYPE
    SYNTAX      Integer32
    MAX-ACCESS read-only
    STATUS      current
    DESCRIPTION
            "The value of the MPEG decoder Presentation TimeStamp
            (PTS). The LSB should be dropped to reduce the PTS length
            to 32 bits."
    ::= { ocStbHostMpeg2ContentEntry 15 }

ocStbHostMpeg2ContentDiscontinuities OBJECT-TYPE
    SYNTAX      Counter32
    MAX-ACCESS read-only
    STATUS      current
    DESCRIPTION
            "The sum of the audio and video PID discontinuities
            detected on the MPEG stream. The values are based on
            the time since PCR lock on the current PIDs or stream being
            reported"
    ::= { ocStbHostMpeg2ContentEntry 16 }

ocStbHostMpeg2ContentPktErrors OBJECT-TYPE
    SYNTAX      Counter32
    MAX-ACCESS read-only
    STATUS      current
    DESCRIPTION
            "The number of errors detected in the MPEG stream. The
             Values are based on the time since PCR lock on the
             Current PIDs or stream being reported"
    ::= { ocStbHostMpeg2ContentEntry 17 }

ocStbHostMpeg2ContentPipelineErrors OBJECT-TYPE
    SYNTAX      Counter32
    MAX-ACCESS read-only
    STATUS      current
    DESCRIPTION
            "The number of errors reported exclusively by the MPEG decoder."
    ::= { ocStbHostMpeg2ContentEntry 18 }

ocStbHostMpeg2ContentDecoderRestarts OBJECT-TYPE
    SYNTAX      Counter32
    MAX-ACCESS read-only
    STATUS      current
    DESCRIPTION
            "The number of times the software driver restarted
            the MPEG decoding process."
    ::= { ocStbHostMpeg2ContentEntry 19 }

--
-- Analog Video Table
--

ocStbHostAnalogVideoTable OBJECT-TYPE
    SYNTAX      SEQUENCE OF OcStbHostAnalogVideoEntry
    MAX-ACCESS not-accessible
    STATUS      current
    DESCRIPTION
            "Contains information about the Analog Video signal.
            Entries in this table can be associated to interfaces
            receiving or forwarding analog content."
    ::= { ocStbHostServiceProgramInfo 4 }

ocStbHostAnalogVideoEntry OBJECT-TYPE
    SYNTAX      OcStbHostAnalogVideoEntry
    MAX-ACCESS not-accessible
    STATUS      current
    DESCRIPTION
            "The conceptual row for this table."
    INDEX { ocStbHostAVInterfaceIndex }
    ::= { ocStbHostAnalogVideoTable 1 }

OcStbHostAnalogVideoEntry ::=
    SEQUENCE {
        ocStbHostAnalogVideoProtectionStatus INTEGER
        }

ocStbHostAnalogVideoProtectionStatus OBJECT-TYPE
    SYNTAX      INTEGER {
                copyProtectionOff(0),
                  splitBurstOff(1),
                  twoLineSplitBurst(2),
                  fourLineSplitBurst(3)
                  }
     MAX-ACCESS   read-only
     STATUS       current
     DESCRIPTION
             "The analog protection system (APS) of this Video content
             entry. The possible values are:
             'copyProtectionOff' means the Macrovision Analog protection
              is off
             'splitBurstOff' means the AGC (Automatic Gain Control)
              is on and the split burst is off.
             'twoLineSplitBurst' means AGC is on with two-line
              split burst.
             'fourLineSplitBurst' means AGC is on with four-line
              split burst.
             This object is instantiated only for A/V output interfaces
             that support APS like but not limited to:
             'ocStbHostRfOutCh', 'ocStbHostSVideoOut' and
             'ocStbHostBbVideoOut'.
             The A/V interfaces 'ocStbHostComponentOut'
             only support 'splitBurstOff' APS mode for the video formats
             'format480i' and 'format480p'."
     ::= { ocStbHostAnalogVideoEntry 1 }

--
-- QPSK Objects
--

ocStbHostQpskObjects OBJECT IDENTIFIER ::= {ocStbHostInterfaces 8}

ocStbHostQpskFDCFreq OBJECT-TYPE
    SYNTAX      Unsigned32
    UNITS       "hertz"
    MAX-ACCESS read-only
    STATUS      current
    DESCRIPTION
            "The frequency to which the QPSK receiver is currently tuned."
    ::= { ocStbHostQpskObjects 1 }

ocStbHostQpskRDCFreq OBJECT-TYPE
    SYNTAX      Unsigned32
    UNITS       "hertz"
    MAX-ACCESS read-only
    STATUS      current
    DESCRIPTION
            "The frequency to which the QPSK transmitter is currently tuned."
    ::= { ocStbHostQpskObjects 2 }

ocStbHostQpskFDCBer OBJECT-TYPE
    SYNTAX      INTEGER
                {
                berGreaterThan10e2(1),
                berRange10e2ToGreaterThan10e4(2),
                berRange10e4ToGreaterThan10e6(3),
                berRange10e6ToGreaterThan10e8(4),
                berRange10e8ToGreaterThan10e12(5),
                berEqualToOrLessThan10e12(6),
                berNotApplicable(7)
                }
    MAX-ACCESS read-only
    STATUS      current
    DESCRIPTION
            "The rate at which bit errors are occurring based on the
            number of data errors since the frequency has been locked."
    ::= { ocStbHostQpskObjects 3 }

ocStbHostQpskFDCStatus OBJECT-TYPE
    SYNTAX      INTEGER
                {
                notLocked(1),
                locked(2)
                }
    MAX-ACCESS read-only
    STATUS      current
    DESCRIPTION
            "Forward data channel lock status."
    ::= { ocStbHostQpskObjects 4 }

ocStbHostQpskFDCBytesRead OBJECT-TYPE
    SYNTAX      Unsigned32
    MAX-ACCESS read-only
    STATUS      current
    DESCRIPTION
            "The number of bytes successfully read since the frequency
            was locked."
    ::= { ocStbHostQpskObjects 5 }

ocStbHostQpskFDCPower OBJECT-TYPE
    SYNTAX      TenthdBmV
    UNITS       "dBmV"
    MAX-ACCESS read-only
    STATUS      current
    DESCRIPTION
            "The power level, in dBmV, of the forward data channel."
    ::= { ocStbHostQpskObjects 6 }

ocStbHostQpskFDCLockedTime OBJECT-TYPE
    SYNTAX      Unsigned32
    UNITS       "seconds"
    MAX-ACCESS read-only
    STATUS      current
    DESCRIPTION
            "The number of seconds that the current FDC frequency
            has been locked."
    ::= { ocStbHostQpskObjects 7 }

ocStbHostQpskFDCSNR OBJECT-TYPE
    SYNTAX      TenthdB
    UNITS       "dB"
    MAX-ACCESS read-only
    STATUS      current
    DESCRIPTION
            "This object allows the manager to retrieve the
            FDC SNR value (1/10 dB)."
    ::= { ocStbHostQpskObjects 8 }

ocStbHostQpskAGC OBJECT-TYPE
    SYNTAX      Unsigned32
    UNITS       "percent"
    MAX-ACCESS read-only
    STATUS      current
    DESCRIPTION
            "This object allows the manager to retrieve the OOB channel
            Automatic Gain Control value (%)."
    ::= { ocStbHostQpskObjects 9 }

ocStbHostQpskRDCPower OBJECT-TYPE
    SYNTAX      TenthdBmV
    UNITS       "dBmV"
    MAX-ACCESS read-only
    STATUS      current
    DESCRIPTION
             "The power output level, in dBmV, of the QPSK transmitter."
     ::= { ocStbHostQpskObjects 10 }

ocStbHostQpskRDCDataRate OBJECT-TYPE
    SYNTAX      INTEGER
                {
                kbps256(1),
                kbps1544(2),
                kbps3088(3)
                }
    MAX-ACCESS read-only
    STATUS      current
    DESCRIPTION
            "The data rate (in kbps) of the RDC."
    ::= { ocStbHostQpskObjects 11 }

--
-- EAS Objects
--

ocStbHostEasObjects OBJECT IDENTIFIER ::= { ocStbHostSystem 3 }
ocStbHostEasCodes   OBJECT IDENTIFIER ::= { ocStbHostEasObjects 1 }

ocStbEasMessageStateCode OBJECT-TYPE
    SYNTAX      Unsigned32 (0..99)
    MAX-ACCESS read-only
    STATUS      current
    DESCRIPTION
            "This object allows the manager to retrieve the
            EAS State Code utilized by the STB. A
            value of 0 indicates that the code is not
            defined, thus the eSTB does not discriminate
            any State Code defined in an EAS message."
    REFERENCE
            "SCTE-18"
    ::= { ocStbHostEasCodes 1 }

ocStbEasMessageCountyCode OBJECT-TYPE
    SYNTAX      Unsigned32 (0..999)
    MAX-ACCESS read-only
    STATUS      current
    DESCRIPTION
            "This object allows the manager to retrieve the
            EAS County Code utilized by the STB. A
            value of 0 indicates that the code is not
            defined, thus the eSTB ignores any County
            Code defined in an EAS message."
    REFERENCE
            "SCTE-18"
    ::= { ocStbHostEasCodes 2 }

ocStbEasMessageCountySubdivisionCode OBJECT-TYPE
    SYNTAX      Unsigned32 (0..9)
    MAX-ACCESS read-only
    STATUS      current
    DESCRIPTION
            "This object allows the manager to retrieve the
            EAS County Sub Code utilized by the STB. A
            value of 0 indicates that the code is not
            defined, thus the eSTB ignores it and any County
            Subdivision Code defined in an EAS message is accepted."
    REFERENCE
            "SCTE-18"
    ::= { ocStbHostEasCodes 3}

--
-- STB security subsystem
--

ocStbHostSecuritySubSystem OBJECT IDENTIFIER ::= { ocStbHostMibObjects 2 }

ocStbHostCASystemIdentifier OBJECT-TYPE
    SYNTAX      SnmpAdminString
    MAX-ACCESS read-only
    STATUS      current
    DESCRIPTION
            "Conditional access system identifier defined by DVB
            and MPEG. This object represents the 16-bit CA_system_id
            obtained from the ca_info_reply apdu. Only the first CAS ID
            value (16-bits) from ca_info()will be reported."
    ::= { ocStbHostSecuritySubSystem 3 }

ocStbHostCAType OBJECT-TYPE
    SYNTAX      INTEGER {
                other(1),
                embedded(2),
                cablecard(3),
                dcas(4)
                }
    MAX-ACCESS read-only
    STATUS      current
    DESCRIPTION
            "The Conditional Access (CA) supported by
            the host device.
            'other' means a CA which is not described by one of
            the other enumerations in this list.
            'embedded' means a vendor-specific embedded CA
            'cablecard' means OpenCable CableCARD is supported.
            'dcas' means software downloadable CA is
            supported."
    ::= { ocStbHostSecuritySubSystem 4 }

--
-- STB Host Software objects
--

ocStbHostSoftware OBJECT IDENTIFIER ::= { ocStbHostMibObjects 3 }

--
-- ocStbHost device Software Requirements
--

ocStbHostDeviceSoftwareBase OBJECT IDENTIFIER ::= { ocStbHostSoftware 1 }
ocStbHostFirmwareDownloadStatus OBJECT IDENTIFIER ::= { ocStbHostSoftware 2 }
ocStbHostSoftwareApplicationInfo OBJECT IDENTIFIER ::= { ocStbHostSoftware 3 }

--
-- Software versions
--

ocStbHostSoftwareFirmwareVersion OBJECT-TYPE
     SYNTAX      SnmpAdminString
     MAX-ACCESS read-only
     STATUS      current
     DESCRIPTION
             "The platform code software version currently operating in
             this device. This object should be in the syntax used by
             the individual vendor to identify software versions. The
             device must return a string descriptive of the current
             software load. This object is shared with
             docsDevSwCurrentVers. For a monolithic download image,
             this object has the same value as docsDevSwCurrentVers
             on the eCM."
     ::= { ocStbHostDeviceSoftwareBase 1 }

ocStbHostSoftwareOCAPVersion OBJECT-TYPE
    SYNTAX      SnmpAdminString
    MAX-ACCESS read-only
    STATUS      current
    DESCRIPTION
            "This object returns a string indicating the latest version
            of the OCAP profile supported by this device, e.g., '1.0'."
    ::= { ocStbHostDeviceSoftwareBase 2 }

ocStbHostSoftwareFirmwareReleaseDate OBJECT-TYPE
    SYNTAX      DateAndTime
    MAX-ACCESS read-only
    STATUS      current
    DESCRIPTION
            "This object returns release date of this entire firmware
            image (the stack OS). The local time fields should be
            set to zero and the timezone information omitted."
    ::= { ocStbHostDeviceSoftwareBase 3 }

--
-- Firmware Download Status
--

ocStbHostFirmwareImageStatus OBJECT-TYPE
    SYNTAX      INTEGER
                {
                imageAuthorized(1),
                imageCorrupted(2),
                imageCertFailure(3),
                imageMaxDownloadRetry(4),
                imageMaxRebootRetry(5)
                }
    MAX-ACCESS read-only
    STATUS      current
    DESCRIPTION
            "This object details the image status recently downloaded
            'imageAuthorized' means the image is valid.
            'imageCorrupted' means the image is invalid.
            'imageCertFailure' means CVC authentication has failed.
            'imageMaxDownloadRetry' means the maximum number of code
            file download retries has been reached. When the value of
            this object is imageMaxDownloadRetry(4), the value of
            ocStbHostSoftwareCodeDownloadStatus must be
            downloadingFailed(3).
            'imageMaxRebootRetry' means the maximum number of reboots
            has occurred after code file download."
    ::= { ocStbHostFirmwareDownloadStatus 1 }

ocStbHostFirmwareCodeDownloadStatus OBJECT-TYPE
    SYNTAX      INTEGER
                {
                downloadingStarted(1),
                downloadingComplete(2),
                  downloadingFailed(3),
                  other(4)
                  }
    MAX-ACCESS    read-only
    STATUS        current
    DESCRIPTION
            "This object details the download status
            of the target image.
            'downloadingComplete' means the image download was
            successful.
            'downloadingFailed' means the image download failed.
            'other' means a status not described by the other
            enumerations."
    ::= { ocStbHostFirmwareDownloadStatus 2 }

ocStbHostFirmwareCodeObjectName OBJECT-TYPE
    SYNTAX      SnmpAdminString
    MAX-ACCESS read-only
    STATUS      current
    DESCRIPTION
            "The file name of the software image to be loaded into this
            device. This object value may optionally contain server
            and path information about the file name when applicable.
            If unknown, the string '(unknown)' is returned. This
            object is shared with docsDevSwFilename."
    ::= { ocStbHostFirmwareDownloadStatus 3 }

ocStbHostFirmwareDownloadFailedStatus OBJECT-TYPE
    SYNTAX      INTEGER
                {
                cdlError1(1),
                cdlError2(2),
                cdlError3(3),
                cdlError4(4),
                cdlError5(5),
                cdlError6(6),
                cdlError7(7),
                cdlError8(8),
                cdlError9(9),
                cdlError10(10),
                cdlError11(11),
                cdlError12(12),
                cdlError13(13),
                cdlError14(14),
                cdlError15(15),
                cdlError16(16),
                cdlError17(17),
                cdlError18(18),
                cdlError19(19),
                cdlError20(20),
                cdlError21(21),
                cdlError22(22),
                cdlError23(23),
                cdlError24(24),
                cdlError25(25),
                cdlError99(99)
                }
    MAX-ACCESS read-only
    STATUS      current
    DESCRIPTION
            "This object details the firmware download
            failed status codes.

             cdlError1, No Failure
             cdlError2, Improper code file controls - CVC subject
                 organizationName for manufacturer does not match the
                 Host device manufacturer name
             cdlError3, Improper code file controls - CVC subject
                 organizationName for code cosigning agent does not
                 match the Host device current code cosigning agent.
             cdlError4, Improper code file controls - The
                 manufacturer's PKCS #7 signingTime value is equal-to
                 or less-than the codeAccessStart value currently held
                 in the Host device.
             cdlError5, Improper code file controls - The
                 manufacturer's PKCS #7 validity start time value is
                 less-than the cvcAccessStart value currently held in
                 the Host device.
             cdlError6, Improper code file controls - The manufacturer's
                 CVC validity start time is less-than the cvcAccessStart
                 value currently held in the Host device.
             cdlError7, Improper code file controls - The manufacturer's
                 PKCS #7 signingTime value is less-than the CVC validity
                 start time.
             cdlError8, Improper code file controls - Missing or
                 improper extendedKeyUsage extension in the
                 manufacturer CVC.
             cdlError9, Improper code file controls - The cosigner's
                 PKCS #7 signingTime value is equal-to or less-than the
                 codeAccessStart value currently held in the
                 Host device.
             cdlError10, Improper code file controls - The cosigner's
                 PKCS #7 validity start time value is less-than the
                 cvcAccessStart value currently held in the Host device.
             cdlError11, Improper code file controls - The cosigner's
                 CVC validity start time is less-than the cvcAccessStart
                 value currently held in the Host device.
             cdlError12, Improper code file controls - The cosigner's
                 PKCS #7 signingTime value is less-than the CVC validity
                 start time.
             cdlError13, Improper code file controls - Missing or
                 improper extended key-usage extension in the cosigner's
                 CVC.
             cdlError14, Code file manufacturer CVC validation failure.
             cdlError15, Code file manufacturer CVS validation failure.
             cdlError16, Code file cosigner CVC validation failure.
             cdlError17, Code file cosigner CVS validation failure.
             cdlError18, Improper eCM configuration file CVC format
                 (e.g., missing or improper key usage attribute).
             cdlError19, eCM configuration file CVC validation failure.
             cdlError20, Improper SNMP CVC format.
             cdlError21, CVC subject organizationName for manufacturer
                 does not match the Host devices manufacturer name.
             cdlError22, CVC subject organizationName for code cosigning
                 agent does not match the Host devices current code
                 cosigning agent.
             cdlError23, The CVC validity start time is less-than or
                 equal-to the corresponding subject's cvcAccessStart
                 value currently held in the Host device.
             cdlError24, Missing or improper key usage attribute.
             cdlError25, SNMP CVC validation failure.
             cdlError99, Other errors. Errors that do not fall into the
                 categories delineated above."
     ::= { ocStbHostFirmwareDownloadStatus 4 }

ocStbHostFirmwareDownloadFailedCount OBJECT-TYPE
    SYNTAX      Counter32
    MAX-ACCESS read-only
    STATUS      current
    DESCRIPTION
            "This object details the number of times the product
            attempted to download the firmware object defined by
            ocStbHostFirmwareCodeObjectName. The value is reset when
            the product attempts to download a new firmware object."
    ::= { ocStbHostFirmwareDownloadStatus 5 }

ocStbHostFirmwareDownloadGroupId OBJECT-TYPE
    SYNTAX      Unsigned32 (0..65535)
    MAX-ACCESS read-only
    STATUS      current
    DESCRIPTION
            "This object specifies the Group Identifier. This is persistent.
            The host may initiate a download if the group identifier in the
            Common Download code version table matches this value. Downloads
            can be triggered using the Common Download code version table
            message for global upgrade of a group of similar hosts. The
            Group Identifier is the same a group_id used in [CDL2]"
    DEFVAL { 0 }
    ::= { ocStbHostFirmwareDownloadStatus 6 }

ocStbHostSoftwareApplicationInfoTable OBJECT-TYPE
    SYNTAX      SEQUENCE OF OcStbHostSoftwareApplicationInfoEntry
    MAX-ACCESS not-accessible
    STATUS      current
    DESCRIPTION
            "This table allows the manager to display and retrieve
            self-diagnostic software information of all available
            applications."
    ::= { ocStbHostSoftwareApplicationInfo 1 }

ocStbHostSoftwareApplicationInfoEntry OBJECT-TYPE
    SYNTAX      OcStbHostSoftwareApplicationInfoEntry
    MAX-ACCESS not-accessible
    STATUS      current
    DESCRIPTION
            "An entry exists for each available application."
    INDEX { ocStbHostSoftwareApplicationInfoIndex }
    ::= { ocStbHostSoftwareApplicationInfoTable 1 }

OcStbHostSoftwareApplicationInfoEntry ::= SEQUENCE {
        ocStbHostSoftwareAppNameString         SnmpAdminString,
        ocStbHostSoftwareAppVersionNumber      SnmpAdminString,
        ocStbHostSoftwareStatus                INTEGER,
        ocStbHostSoftwareApplicationInfoIndex Unsigned32,
        ocStbHostSoftwareOrganizationId        OCTET STRING,
        ocStbHostSoftwareApplicationId         OCTET STRING
        }

ocStbHostSoftwareAppNameString OBJECT-TYPE
    SYNTAX      SnmpAdminString
    MAX-ACCESS read-only
    STATUS      current
    DESCRIPTION
            "The application’s name string."
    ::= { ocStbHostSoftwareApplicationInfoEntry 1 }

ocStbHostSoftwareAppVersionNumber OBJECT-TYPE
    SYNTAX      SnmpAdminString
    MAX-ACCESS read-only
    STATUS      current
    DESCRIPTION
            "The application’s version number."
    ::= { ocStbHostSoftwareApplicationInfoEntry 2 }

ocStbHostSoftwareStatus OBJECT-TYPE
    SYNTAX      INTEGER
                {
                loaded(4),
                notLoaded(5),
                paused(6),
                running(7),
                destroyed(8)
                }
     MAX-ACCESS read-only
     STATUS     current
     DESCRIPTION
             "The software status of the application."
     ::= { ocStbHostSoftwareApplicationInfoEntry 3 }

ocStbHostSoftwareApplicationInfoIndex OBJECT-TYPE
    SYNTAX      Unsigned32 (1..4294967295)
    MAX-ACCESS not-accessible
    STATUS      current
    DESCRIPTION
            "Table Index added in this position (4) because it
            replaced an external index."
    ::= { ocStbHostSoftwareApplicationInfoEntry 4 }

ocStbHostSoftwareOrganizationId OBJECT-TYPE
    SYNTAX      OCTET STRING (SIZE(4))
    MAX-ACCESS read-only
    STATUS      current
    DESCRIPTION
            "Organization ID captured in the XAIT or AIT."
    ::= { ocStbHostSoftwareApplicationInfoEntry 5 }

ocStbHostSoftwareApplicationId OBJECT-TYPE
    SYNTAX      OCTET STRING (SIZE(2))
    MAX-ACCESS read-only
    STATUS      current
    DESCRIPTION
            "This 16 bit field uniquely identifies the
            application function as assigned by the
            responsible/owning organization identified in
            ocStbHostSoftwareOrganizationId."
    ::= { ocStbHostSoftwareApplicationInfoEntry 6 }

ocStbHostSoftwareApplicationInfoSigLastReceivedTime OBJECT-TYPE
    SYNTAX      DateAndTime
    MAX-ACCESS read-only
    STATUS      current
    DESCRIPTION
            "Indicates the last time an XAIT was received from the
            network that was not the same version as already in-use.
            If the host device has not received an XAIT, then this
            returns a date and time of all zeros.
              - This must be updated ONLY when an XAIT is received
                from the network (e.g., not when loaded from persistent
                storage).
              - This must NOT be updated if an XAIT is received that
                has a version the same as the currently in-use version,
                UNLESS the in-use XAIT was loaded from persistent storage
                AND it is the FIRST time receiving an XAIT from the network
                without error.
              - This must NOT be updated if XAIT is received with a
                status of error(2).
              - This must be updated each time an XAIT is received for
                resulting in a status of okayButRejected(3).
              - This must be updated if an XAIT is received from the
                network resulting in a status of okay(1) AND its version
                is different than the currently in-use
                version."
    ::= { ocStbHostSoftwareApplicationInfo 2 }

ocStbHostSoftwareApplicationInfoSigLastReadStatus OBJECT-TYPE
    SYNTAX      INTEGER
                {
                unknown(0),
                okay(1),
                error(2),
                okayButRejected(3)
                }
    MAX-ACCESS read-only
    STATUS      current
    DESCRIPTION
            "Indicates the status of the last attempted read of the
            XAIT from the network that was not the same version as
            already in use except as noted below. Reports unknown(0)
            if no XAIT has been received. A value of okayButRejected
            means it was read without errors, but the monitor application
            has rejected it.
              - This must be updated ONLY when an XAIT is received
                from the network (e.g., not when loaded from persistent
                storage).
              - This must NOT be updated if an XAIT is received that has
                a version equal to the currently in-use version, UNLESS
                the in-use XAIT was loaded from persistent storage AND
                it is the FIRST time receiving an XAIT from the network
                without error.
              - The value of unknown(0) must be the initial value before
                any XAIT is ever received from the network.
              - This must NOT be set to unknown(0) if it has ever been set
                to another value."
    ::= { ocStbHostSoftwareApplicationInfo 3 }

ocStbHostSoftwareApplicationInfoSigLastNetworkVersionRead OBJECT-TYPE
    SYNTAX      Integer32 (-1 | 0..31)
    MAX-ACCESS read-only
    STATUS      current
    DESCRIPTION
            "The version number of the XAIT that was last read
            successfully from the network, but not necessarily
            accepted by the monitor app. (LastReadStatus of okay
            or okayButRejected.) The version within the XAIT is
            a 5-bit unsigned integer (range 0..31), but if no XAIT
            has been read from the network, the value reported must
            be -1. (NOTE: Technically, each section has its own
            version number; however, they are required to all be the
            same, so this may be extracted from the first section.)
            If this is -1 and VersionInUse is not -1, it can be
            inferred that the version in use was loaded from
            persistent storage; however, if both versions are the
            same, it cannot be inferred that the initially used XAIT
            did not come from persistent storage."
    ::= { ocStbHostSoftwareApplicationInfo 4 }

ocStbHostSoftwareApplicationInfoSigVersionInUse OBJECT-TYPE
    SYNTAX      Integer32 (-1 | 0..31)
    MAX-ACCESS read-only
     STATUS      current
     DESCRIPTION
             "The version number of the XAIT that is in use, which may
             have been read from the network or from persistent storage.
             The version within the XAIT is a 5-bit unsigned integer
             (range 0..31), but if no XAIT has been read from the network,
             the value reported must be -1. (NOTE: Technically, each
             section has its own version number; however, they are required
             to all be the same, so this may be extracted from the first
             section.) If this is not -1 and LastVersionHeard is -1, it
             can be inferred that the version in use was loaded from
             persistent storage; however, if both versions are the
             same, it cannot be inferred that the initially used XAIT
             did not come from persistent storage."
     ::= { ocStbHostSoftwareApplicationInfo 5 }

--
-- ocStbHost Status Information
--

ocStbHostStatus OBJECT IDENTIFIER ::= { ocStbHostMibObjects 4 }

--
-- Host Power resources
--

ocStbHostPower   OBJECT IDENTIFIER ::= { ocStbHostStatus 1 }

ocStbHostPowerStatus OBJECT-TYPE
    SYNTAX      INTEGER
                {
                powerOn(1),
                standby(2)
                }
    MAX-ACCESS read-only
    STATUS      current
    DESCRIPTION
            "Indicates the current power status of the ocStbHost."
    ::= { ocStbHostPower 1 }

--
-- Host system resources
--

ocStbHostSystemObjects     OBJECT IDENTIFIER ::= { ocStbHostStatus 3 }


ocStbHostSystemMemoryReportTable OBJECT-TYPE
    SYNTAX      SEQUENCE OF OcStbHostSystemMemoryReportEntry
    MAX-ACCESS not-accessible
    STATUS      current
    DESCRIPTION
            "This table contains the Id of each memory type
            reported by the ocStbHost."
    ::= { ocStbHostSystemObjects 3 }

ocStbHostSystemMemoryReportEntry OBJECT-TYPE
    SYNTAX      OcStbHostSystemMemoryReportEntry
    MAX-ACCESS not-accessible
    STATUS      current
    DESCRIPTION
            "Conceptual row of a memory type reported
            by the ocStbHost."
    INDEX { ocStbHostSystemMemoryReportIndex }
    ::= { ocStbHostSystemMemoryReportTable 1 }

OcStbHostSystemMemoryReportEntry::= SEQUENCE {
        ocStbHostSystemMemoryReportIndex           Unsigned32,
        ocStbHostSystemMemoryReportMemoryType      INTEGER,
        ocStbHostSystemMemoryReportMemorySize      Integer32
        }

ocStbHostSystemMemoryReportIndex OBJECT-TYPE
    SYNTAX      Unsigned32(1..4294967295)
    MAX-ACCESS not-accessible
    STATUS      current
    DESCRIPTION
            "The identifier of the memory type."
    ::= { ocStbHostSystemMemoryReportEntry 1 }

ocStbHostSystemMemoryReportMemoryType OBJECT-TYPE
    SYNTAX      INTEGER
                {
                rom(1),
                dram(2),
                sram(3),
                flash(4),
                nvm(5),
                videomemory(7),
                othermemory(8),
                reserved(9),
                internalHardDrive(10),
                externalHardDrive(11),
                opticalMedia(12)
                }
    MAX-ACCESS read-only
    STATUS      current
    DESCRIPTION
            "Designates the type of memory that is being reported."
    ::= { ocStbHostSystemMemoryReportEntry 2 }

ocStbHostSystemMemoryReportMemorySize OBJECT-TYPE
    SYNTAX      Integer32
    UNITS       "kilobytes"
    MAX-ACCESS read-only
    STATUS      current
    DESCRIPTION
            "Designates the physical size of the reported memory type.
            The units are kilobytes, defined to be 1,024 bytes."
    ::= { ocStbHostSystemMemoryReportEntry 3 }

--
-- Host and Card Information
--
ocStbCardInfo OBJECT IDENTIFIER ::= { ocStbHostStatus 4 }

ocStbHostCardMacAddress OBJECT-TYPE
    SYNTAX      MacAddress
    MAX-ACCESS read-only
    STATUS      current
    DESCRIPTION
            "The Mac Address associated with the Card."
    ::= { ocStbCardInfo 1 }

ocStbHostCardIpAddressType OBJECT-TYPE
    SYNTAX      InetAddressType
    MAX-ACCESS read-only
    STATUS      current
    DESCRIPTION
            "The network address Type of ocStbHostCardIpAddress.
            If the Host does not have the Card’s IP address (e.g.,
            the Card has not opened an IP Unicast Flow, which would
            require the Host to obtain the Card’s IP address, thus
            providing the Host with knowledge of the Card’s IP address
            type), then the Host replies with a value of unknown (0)."
    ::= { ocStbCardInfo 2 }

ocStbHostCardIpAddress OBJECT-TYPE
    SYNTAX      InetAddress
    MAX-ACCESS read-only
    STATUS      current
    DESCRIPTION
            "The network address of the Card. If the Host does not
            have the Card’s IP address (e.g., the Card has not opened
            an IP Unicast Flow, which would require the Host to obtain
            the Card’s IP address, thus providing the Host with
            knowledge of the Card’s IP address), then the Host replies
            with a value of zero (00)."
    ::= { ocStbCardInfo 3 }

ocStbHostCCMMI OBJECT IDENTIFIER ::= { ocStbCardInfo 5 }

ocStbHostCCApplications OBJECT IDENTIFIER ::= { ocStbHostCCMMI 1 }

ocStbHostCCAppInfoTable OBJECT-TYPE
    SYNTAX      SEQUENCE OF OcStbHostCCAppInfoEntry
    MAX-ACCESS not-accessible
    STATUS      current
    DESCRIPTION
            "This table allows the manager to retrieve
            the HTML pages for Card applications retrieved by the
            Host using the Application Info resource."
    ::= { ocStbHostCCApplications 1 }

ocStbHostCCAppInfoEntry OBJECT-TYPE
    SYNTAX      OcStbHostCCAppInfoEntry
    MAX-ACCESS not-accessible
    STATUS      current
    DESCRIPTION
            "The conceptual row for this table."
    INDEX { ocStbHostCCApplicationType }
    ::= { ocStbHostCCAppInfoTable 1 }

OcStbHostCCAppInfoEntry ::=
    SEQUENCE {
             ocStbHostCCAppInfoIndex
                 Unsigned32,
             ocStbHostCCApplicationType
                 Unsigned32,
             ocStbHostCCApplicationName
                SnmpAdminString,
            ocStbHostCCApplicationVersion
                Unsigned32,
            ocStbHostCCAppInfoPage
                OCTET STRING
            }

ocStbHostCCAppInfoIndex OBJECT-TYPE
    SYNTAX      Unsigned32
    MAX-ACCESS read-only
    STATUS      current
    DESCRIPTION
            "This object was the index for this table
            in a previous version of the MIB.
            Currently used only as a placeholder to
            avoid changing OID values."
    ::= { ocStbHostCCAppInfoEntry 1 }

ocStbHostCCApplicationType OBJECT-TYPE
    SYNTAX      Unsigned32(0..4294967295)
    MAX-ACCESS read-only
    STATUS      current
    DESCRIPTION
            "Index for this table.
            Contains the application_type field
            in the application_info_cnf() APDU."
    ::= { ocStbHostCCAppInfoEntry 2 }

ocStbHostCCApplicationName OBJECT-TYPE
    SYNTAX      SnmpAdminString
    MAX-ACCESS read-only
    STATUS      current
    DESCRIPTION
            "Contains the application name."
    ::= { ocStbHostCCAppInfoEntry 3 }

ocStbHostCCApplicationVersion OBJECT-TYPE
    SYNTAX      Unsigned32
    MAX-ACCESS read-only
    STATUS      current
    DESCRIPTION
            "Contains the application version."
    ::= { ocStbHostCCAppInfoEntry 4 }

ocStbHostCCAppInfoPage OBJECT-TYPE
    SYNTAX      OCTET STRING
    MAX-ACCESS read-only
    STATUS      current
    DESCRIPTION
            "All HTML data for this application.
            If a 'page' as reported from the Card contains
            links, the links shall be traversed, and all
            HTML from each page traversed shall be included
            in a single, valid HTML string (with per-page
            start/end HTML and BODY tags removed). The resulting
            HTML SHOULD be structured as an HTML table
            consisting of one column, with one row for each
            'page' from the Card. If the full HTML from the
            application (all pages concatenated) will not fit
            within the SNMP buffer, text indicating this
            SHALL follow the table; otherwise nothing except
            the close BODY and HTML tags SHOULD follow the table."
    ::= { ocStbHostCCAppInfoEntry 5 }

ocStbHostSnmpProxyInfo OBJECT IDENTIFIER ::= { ocStbCardInfo 6 }

ocStbHostCardMfgId OBJECT-TYPE
    SYNTAX      OCTET STRING (SIZE(2))
    MAX-ACCESS read-only
    STATUS      current
    DESCRIPTION
            "The two-byte manufacturer identifier
            acquired from the CableCard. The high order byte
            defines the manufacturer as follows.
                00xx = Motorola
                01xx = Cisco (Scientific-Atlanta)
                02xx = NDS
                03xx = Conax
            This can be used with version and root OID to enable
            SNMP access to proprietary CC diagnostic information.
            The lower order octet can be used to privately identify
            product generation and derivatives."
    ::= { ocStbHostSnmpProxyInfo 1 }

ocStbHostCardVersion OBJECT-TYPE
    SYNTAX      OCTET STRING (SIZE (2))
    MAX-ACCESS read-only
    STATUS      current
    DESCRIPTION
            "The version of the CableCard. This can be used with
            manufacturer and root OID to enable SNMP access to
            proprietary diagnostic information."
    ::= { ocStbHostSnmpProxyInfo 2 }

ocStbHostCardRootOid OBJECT-TYPE
    SYNTAX      OBJECT IDENTIFIER
    MAX-ACCESS read-only
    STATUS      current
    DESCRIPTION
            "An ASN.1 encoding of the root OID of the
            CableCARD MIB defined in the CC Manufacturers private
            MIB name space. This OID will be compared against each
            object identifier in the VARBIND contained within the
            GetRequests, GetNextRequests, GetBulkRequests, and
            SetRequests received by the Host2.x if the objects are not
            in the Host2.x MIB. A match of OIDs root requires the Host
            to send a corresponding request to the Card. A 0.0 value
            explicitly states the Card does not support SNMP message
            processing."
    ::= { ocStbHostSnmpProxyInfo 3 }

ocStbHostCardSerialNumber OBJECT-TYPE
    SYNTAX      SnmpAdminString
    MAX-ACCESS read-only
    STATUS      current
    DESCRIPTION
            "Serial Number of CableCARD."
    ::= { ocStbHostSnmpProxyInfo 4 }

ocStbHostCardSnmpAccessControl OBJECT-TYPE
    SYNTAX      TruthValue
    MAX-ACCESS read-write
    STATUS      current
    DESCRIPTION
            "This object allows the manager to control access to the
            Card's MIB via networked devices (e.g., get/set by network
            attached managers). It has no impact on local
            access (e.g., application get/set of Card MIB objects).

             When set to TRUE, the Host is permitted to forward
             SNMP messages received on the WAN/LAN interface addressed
             to the OID of the Card subtree.

             When set to FALSE, the Host must discard and not forward
            to the Card any SNMP messages received on the WAN/LAN
            interface addressed to the OID of the Card subtree.

             Default of this object is TRUE."
     DEFVAL { 1 }
     ::= { ocStbHostSnmpProxyInfo 5 }

ocStbHostCardId OBJECT-TYPE
    SYNTAX      DisplayString (SIZE(17))
    MAX-ACCESS read-only
    STATUS      current
    DESCRIPTION
            "Allows the manager to retrieve the 40 least-significant
            Bits of the CableCARD ID in the string
            format indicated below:

            M-MMU-UUU-UUU-UUL

            Where:

            M-MM is the decimal representation of the
            10-bit CHICA assigned manufacturer number.

            U-UUU-UUU-UU is the decimal representation
            of the 30-bit manufacturer assigned unit number.

            L is a Luhn check digit calculated over the
            preceding 12 decimal digits.

             If the Card ID is unknown, then the string shall
             be all zeros e.g., '0-000-000-000-000'."
     ::= { ocStbCardInfo 7 }

ocStbHostCardBindingStatus OBJECT-TYPE
    SYNTAX      INTEGER {
                unknown(1),
                invalidCertificate(2),
                otherAuthFailure(3),
                bound(4)
                }
    MAX-ACCESS read-only
    STATUS      current
    DESCRIPTION
            "The status of CableCARD/Host mutual authentication
            and binding.

             ‘unknown’ means the binding state has not been determined.
                  For example, mutual authentication may not have
                  commenced or may be in process.
             ‘invalidCertificate’ means the Host failed to establish
                  device certificate authenticity.
             ‘otherAuthFailure’ corresponds to other failures in
                  establishing mutual authentication.
             ‘bound’ indicates that mutual authentication has succeeded
                  and CableCARD and Host are bound successfully."
     ::= { ocStbCardInfo 8 }

ocStbHostCardOpenedGenericResource OBJECT-TYPE
    SYNTAX      OCTET STRING (SIZE (4))
    MAX-ACCESS read-only
    STATUS      current
    DESCRIPTION
            "The hexadecimal representation of the generic feature
            control resource number opened using a profile
            reply() APDU resource_identifier field. The
            possible values are defined in the [CCIF]
            specification."
    ::= { ocStbCardInfo 9 }

ocStbHostCardTimeZoneOffset OBJECT-TYPE
    SYNTAX      INTEGER(-12..12)
    MAX-ACCESS read-only
    STATUS      current
    DESCRIPTION
            "Decimal value of the UTC offset taken from the
            feature_parameters() APDU for feature_id =5 where
            possible values are defined in the [CCIF]
            specification."
    ::= { ocStbCardInfo 10 }

ocStbHostCardDaylightSavingsTimeDelta OBJECT-TYPE
    SYNTAX      OCTET STRING (SIZE (1))
    MAX-ACCESS read-only
    STATUS      current
    DESCRIPTION
            "Decimal value of the daylight savings delta.
            A 0x00 should be returned if the Card does not
            support this feature or if there is no delta.
            The ambiguity may be resolved by querying
            ocStbHostCardDaylightSavingsTimeEntry object."
    ::= { ocStbCardInfo 11 }

ocStbHostCardDaylightSavingsTimeEntry OBJECT-TYPE
    SYNTAX      Unsigned32
    MAX-ACCESS read-only
    STATUS      current
    DESCRIPTION
            "Daylight savings entry time given as time lapsed
            since 12 AM Jan 6, 1980, in units of GPS seconds.
            All zeros should be returned if the Card does not
            support this feature."
    ::= { ocStbCardInfo 12 }

ocStbHostCardDaylightSavingsTimeExit OBJECT-TYPE
    SYNTAX      Unsigned32
    MAX-ACCESS read-only
    STATUS      current
    DESCRIPTION
            "Daylight savings exit time given as time lapsed
            since 12 AM Jan 6, 1980, in units of GPS seconds.
            All zeros should be returned if the Card does not
            support this feature."
    ::= { ocStbCardInfo 13 }

ocStbHostCardEaLocationCode OBJECT-TYPE
    SYNTAX      OCTET STRING (SIZE(3))
    MAX-ACCESS read-only
    STATUS      current
    DESCRIPTION
            "Contains the EA location codes as defined
            in American National Standard, J-STD-042.
            The bits corresponding to ANSI EA location codes
            are indicated below:

             SSSSSSSS-DDDD-xx-CCCCCCCCCC

             Where:

             SSSSSSSS is An 8-bit unsigned number in the
             range 0 to 99 that represents the State or
             Territory affected by the emergency alert.

             DDDD is A 4-bit number in the range 0 to 9
             that defines county subdivisions.

            xx is reserved

            CCCCCCCCCC is 10-bit number between 0 to 999
            that identifies a county within a state.

             If the EA_Location code is unknown, then the string shall
             be all zeros e.g., '000000'."
     ::= { ocStbCardInfo 14 }

ocStbHostCardVctId OBJECT-TYPE
    SYNTAX      OCTET STRING (SIZE(2))
    MAX-ACCESS read-only
    STATUS      current
    DESCRIPTION
            "Display the VTC-ID if supported. If not supported
            then return 0x0000."
    ::= { ocStbCardInfo 15 }

ocStbHostCardCpInfo OBJECT IDENTIFIER ::= { ocStbCardInfo 16 }

ocStbHostCardCpAuthKeyStatus OBJECT-TYPE
    SYNTAX      INTEGER {
                ready(1),
                notReady(2)
                }
    MAX-ACCESS read-only
    STATUS      current
    DESCRIPTION
            "This parameter SHALL be set to “Ready” if the
            Card has requested the host’s authentication
            key via the APDU CP_data_req() with a
            Datatype_id = 22. This parameter SHALL be set
            to “Not Ready” if the Cablecard has NOT
            requested the authentication key."
    ::= { ocStbHostCardCpInfo 1 }

ocStbHostCardCpCertificateCheck OBJECT-TYPE
    SYNTAX      INTEGER {
                ok(1),
                failed(2)
                }
    MAX-ACCESS read-only
    STATUS      current
    DESCRIPTION
            "Display the results of the Card_DevCert verification
            as defined in the OpenCable CableCard Copy Protection
            Specification."
    ::= { ocStbHostCardCpInfo 2 }

ocStbHostCardCpCciChallengeCount OBJECT-TYPE
    SYNTAX      Counter32
    MAX-ACCESS read-only
    STATUS      current
    DESCRIPTION
            "Display the Card CCI Challenge message
            count [CCCP] since the
            last boot or reset."
    ::= { ocStbHostCardCpInfo 3 }

ocStbHostCardCpKeyGenerationReqCount OBJECT-TYPE
    SYNTAX      Counter32
    MAX-ACCESS read-only
    STATUS      current
    DESCRIPTION
            "Display the Copy Protection Key Generation
            Request count [CCCP] since
            the last boot or reset."
    ::= { ocStbHostCardCpInfo 4 }

ocStbHostCardCpIdList OBJECT-TYPE
    SYNTAX      OCTET STRING (SIZE(4))
    MAX-ACCESS read-only
    STATUS      current
    DESCRIPTION
            "Display the CP_system_id_bitmask field of the
            APDU CP_open_cnf() as defined in the CableCARD Copy
            Protection Specification Section 11.3.1.2."
    ::= { ocStbHostCardCpInfo 5 }

ocStbHostInfo OBJECT IDENTIFIER ::= { ocStbHostStatus 5 }

ocStbHostIpAddressType OBJECT-TYPE
    SYNTAX      InetAddressType
    MAX-ACCESS read-only
    STATUS      current
    DESCRIPTION
            "This object was the address type for ocStbHostIpAddress,
            which was never implemented in a previous version of the
            MIB. Currently used only as a placeholder to avoid
            changing OID values."
    ::= { ocStbHostInfo 1 }

ocStbHostIpSubNetMask OBJECT-TYPE
    SYNTAX      InetAddress
    MAX-ACCESS read-only
    STATUS      current
    DESCRIPTION
            "The IP subnet mask of the Host address."
    ::= { ocStbHostInfo 2 }

ocStbHostOobMessageMode OBJECT-TYPE
    SYNTAX      INTEGER
                {
                scte55(1),
                dsg(2),
                other(3)
                }
    MAX-ACCESS read-only
    STATUS      current
    DESCRIPTION
            "Out of Band Messaging communications mode currently
            employed by the Host2.x."
    ::= { ocStbHostInfo 3 }

ocStbHostDumpTrapInfo OBJECT IDENTIFIER ::= { ocStbHostInfo 4 }

ocStbHostDumpEventCount OBJECT-TYPE
    SYNTAX      INTEGER(0..32)
    MAX-ACCESS read-write
    STATUS      current
    DESCRIPTION
            "The number of times the host should notify the headend(s)
            of a dump condition (e.g., stack dumps after boot).
            When an exception occurs, if ocStbHostDumpEventCount is
            non-zero, the host will send the notification to each
            defined notification receiver and decrement
            ocStbHostDumpEventCount. A non-zero count arms the trap.
            No trap will be sent if the value is 0."
    DEFVAL { 0 }
    ::= { ocStbHostDumpTrapInfo 1 }

ocStbHostDumpNow OBJECT-TYPE
    SYNTAX      TruthValue
     MAX-ACCESS read-write
     STATUS      current
     DESCRIPTION
             "True(1) forces an immediate dump of a component of the
             Host. The Host will prepare the dump file then send the
             Notification-PDU to the headend. This simulates
             the manufacturer-defined event that would cause a dump.
             Reading this object returns false(2)."
     ::= { ocStbHostDumpTrapInfo 2 }

ocStbHostDumpEventTimeout OBJECT-TYPE
    SYNTAX      Unsigned32(1..120)
    MAX-ACCESS read-write
    STATUS      current
    DESCRIPTION
            "The time, in seconds, after a SNMPv2-Trap-PDU as been sent
            to the headend that the Host will wait before abandoning
            the dump transfer. If the Host does not receive a TFTP Get
            from the headend within this timeout period, it will
            proceed with the manufacturer-defined recovery process
            from the condition that caused the dump. The intent is to
            prevent the Host from waiting indefinitely for a TFTP
            session to enable the dump transfer. The timer should be
            ignored if the Host receives a TFTP GET from the headend
            within the timeout period. The default timeout value
            is 5 seconds."
    DEFVAL { 5 }
    ::= { ocStbHostDumpTrapInfo 3 }

ocStbHostDumpFilePath OBJECT-TYPE
SYNTAX      SnmpAdminString
MAX-ACCESS read-only
STATUS      current
DESCRIPTION
        "Dump file path and name."
    ::= { ocStbHostDumpTrapInfo 4 }

ocStbHostSpecificationsInfo OBJECT IDENTIFIER ::= { ocStbHostInfo 5 }

ocStbHostCfrSpecificationIssue OBJECT-TYPE
    SYNTAX      SnmpAdminString
    MAX-ACCESS read-only
    STATUS      current
    DESCRIPTION
            "The Host CFR version implemented in this
            device (e.g., OC-SP-HOST2.1-CFR-I06-081114)."
    ::= { ocStbHostSpecificationsInfo 1 }

ocStbHostMibSpecificationIssue OBJECT-TYPE
    SYNTAX      SnmpAdminString
    MAX-ACCESS read-only
    STATUS      current
    DESCRIPTION
            "The version implemented in this device
            (e.g., OC-SP-MIB-HOST2.X-I05-081114)."
    ::= { ocStbHostSpecificationsInfo 2 }

ocStbHostBootStatus OBJECT-TYPE
    SYNTAX      INTEGER
                {
                completedSuccessfully(1),
                completeWithErrors(2),
                inProgressWithCodeDownload(3),
                inProgressNoCodeDownload(4),
                inProgressAwaitingMonitorApp(5),
                unknown(6)
                }
    MAX-ACCESS read-only
    STATUS      current
    DESCRIPTION
            "Defines the current status of the host during or after
            boot process."
    ::= { ocStbHostInfo 6 }

ocStbHostContentErrorSummaryInfo OBJECT IDENTIFIER ::= { ocStbHostInfo 7 }

ocStbHostPatTimeoutCount OBJECT-TYPE
    SYNTAX      Counter32
    MAX-ACCESS read-only
    STATUS      current
    DESCRIPTION
            "These values increment every time a PAT timeout
            condition has occurred since the last boot or reset."
    ::= { ocStbHostContentErrorSummaryInfo 1 }

ocStbHostPmtTimeoutCount OBJECT-TYPE
    SYNTAX      Counter32
    MAX-ACCESS read-only
    STATUS      current
    DESCRIPTION
            "These values increment every time a PMT timeout
            condition has occurred since the last boot or reset."
    ::= { ocStbHostContentErrorSummaryInfo 2 }

ocStbHostOobCarouselTimeoutCount OBJECT-TYPE
    SYNTAX      Counter32
    MAX-ACCESS read-only
    STATUS      current
    DESCRIPTION
            "These values increment each time an implementation
            specific OOB Carousel timeout has occurred since the last
            boot or reset."
    ::= { ocStbHostContentErrorSummaryInfo 3 }

ocStbHostInbandCarouselTimeoutCount OBJECT-TYPE
    SYNTAX      Counter32
    MAX-ACCESS read-only
    STATUS      current
    DESCRIPTION
            "These values increment each time an implementation
            specific Inband Carousel timeout has occurred since the
            last boot or reset."
    ::= { ocStbHostContentErrorSummaryInfo 4 }

ocStbHostRebootInfo OBJECT IDENTIFIER ::= { ocStbHostStatus 6 }

ocStbHostRebootType OBJECT-TYPE
    SYNTAX      INTEGER
                {
                unknown(0),
                davicDocsis(1),
                user(2),
                system(3),
                trap(4),
                silentWatchdog(5),
                bootloader(6),
                powerup(7),
                hostUpgrade(8),
                hardware(9),
                cablecardError(10)
                }
    MAX-ACCESS read-only
    STATUS      current
    DESCRIPTION
           "Describes the type of reboot that occurred the last time
           the host device rebooted.

           Unknown(0), unknown reboot. 0 is used as a sentinel value
           to denote that the reboot reporting mechanism is
           initialized and ready for use. If it appears in a reboot
           report as a reboot reason, it means that something
           (of unknown cause) prevented a reboot reason from being
           saved. This is a spontaneous reboot.

           Davic/DOCSIS(1), Davic/DOCSIS switch. The set-top rebooted
           because the network switched from Davic to DOCSIS or
           vice versa. This is a controlled reboot.

           User(2), User reboot. The set-top rebooted at the specific
           request of the user, typically the MSO, but can also be the
           subscriber. Includes, but not limited to, headend-initiated
           reboots, pass-thru and SNMP messages to reboot, new
           application versions that require a reboot in order to
           reload, the staging toolkit, hard disk re-format requests,
           CableCARD inserted or firmware upgrade, and more.
           This is a controlled reboot.

           System(3), System reboot. The set-top rebooted because its
           software determined it cannot continue operation. This can
           be due to any number of reasons, including: detection of
           logic errors, exhaustion of various system resources,
           detection of memory corruption, and more. This is a
           spontaneous reboot.

           Trap(4), Trap reboot. A fatal error detected by the CPU.
           This varies between CPU manufacturers; some possible causes
           are illegal address references, misaligned instruction or
           data access, memory protection violations, attempt to
           decode an unrecognized instruction, etc. This is a
           spontaneous reboot.

           Silent or Watchdog(5). Depending on platform, this is
           either a Silent Reboot (A reboot of unknown origin that
           reports no information) or a Watchdog reboot. This is a
           spontaneous reboot.

           Bootloader(6), Bootloader reboot. For use by bootloader
           software. This is a spontaneous reboot.

           PowerUp(7), Power-up reboot. The set-top rebooted because
           power was lost and then restored. This is a controlled
           reboot.

           Upgrade(8), Upgrade Reboot due to loading new resident
           set-top software. This is a controlled reboot.

           Hardware(9), Hardware Reset reboot. This depends on the
           design of a particular set-top. It might be due to a
           hardware reset line being triggered or by a button push of
           some kind. Manufacturers sometimes provide a way to
           hard reset a box besides removing power. This is a
           spontaneous reboot.

            CablecardError(10), CablecardError. The Host rebooted
            because the communication with the CableCARD was lost and
            could not be reestablished."
     ::= { ocStbHostRebootInfo 1 }

ocStbHostRebootReset OBJECT-TYPE
    SYNTAX      TruthValue
    MAX-ACCESS read-write
    STATUS      current
    DESCRIPTION
            "Setting this object to true(1) causes the device to reset,
            equivalent to a power reset. Reading this object always
            returns false(2)."
    ::= { ocStbHostRebootInfo 2 }

ocStbHostMemoryInfo OBJECT IDENTIFIER ::= { ocStbHostStatus 7 }

ocStbHostLargestAvailableBlock OBJECT-TYPE
    SYNTAX      Integer32
    UNITS       "kilobytes"
    MAX-ACCESS read-only
    STATUS      current
    DESCRIPTION
            "The largest available continuous block of DRAM available
            on the host device, in kilobytes."
    ::= { ocStbHostMemoryInfo 1 }

ocStbHostTotalVideoMemory OBJECT-TYPE
    SYNTAX      Integer32
    UNITS       "kilobytes"
    MAX-ACCESS read-only
    STATUS      current
    DESCRIPTION
            "The total amount of DRAM dedicated to video decoding and
            display on the host device, in kilobytes."
    ::= { ocStbHostMemoryInfo 2 }

ocStbHostAvailableVideoMemory OBJECT-TYPE
    SYNTAX      Integer32
    UNITS       "kilobytes"
    MAX-ACCESS read-only
    STATUS      current
    DESCRIPTION
            "The total amount of DRAM dedicated to video decoding and
            display on the host device that is not allocated and
            available for use, in kilobytes."
    ::= { ocStbHostMemoryInfo 3 }

ocStbHostJVMInfo OBJECT IDENTIFIER ::= { ocStbHostStatus 8 }

ocStbHostJVMHeapSize OBJECT-TYPE
    SYNTAX      Integer32
    UNITS       "kilobytes"
    MAX-ACCESS read-only
    STATUS      current
    DESCRIPTION
            "The total amount of DRAM allocated to the Java Virtual
            Machine heap. The units are kilobytes, defined to be
            1,024 bytes."
    ::= { ocStbHostJVMInfo 1 }

ocStbHostJVMAvailHeap OBJECT-TYPE
    SYNTAX      Integer32
    UNITS       "kilobytes"
    MAX-ACCESS read-only
    STATUS      current
    DESCRIPTION
            "The amount of DRAM in the Java Virtual Machine heap that
            is not allocated and is available for use.
            The units are kilobytes, defined to be 1,024 bytes."
    ::= { ocStbHostJVMInfo 2 }

ocStbHostJVMLiveObjects OBJECT-TYPE
    SYNTAX      Integer32
    MAX-ACCESS read-only
     STATUS      current
     DESCRIPTION
             "The number of active object instances in the Java Virtual
             Machine that are reachable from running code."
     ::= { ocStbHostJVMInfo 3 }

ocStbHostJVMDeadObjects OBJECT-TYPE
    SYNTAX      Integer32
    MAX-ACCESS read-only
    STATUS      current
    DESCRIPTION
            "The number of object instances in the Java Virtual Machine
            that are NOT reachable from running Code."
    ::= { ocStbHostJVMInfo 4 }

-- Conformance information

ocStbHostConformance OBJECT IDENTIFIER ::= { ocStbHostMibModule 2 }
ocStbHostMIBCompliances OBJECT IDENTIFIER ::= { ocStbHostConformance 1 }
ocStbHostMIBGroups OBJECT IDENTIFIER ::= { ocStbHostConformance 2 }

-- Compliance statements

ocStbHostMIBCompliance MODULE-COMPLIANCE
    STATUS      current
    DESCRIPTION
            "The requirements for conformance to the OpenCable
            Set-top HOST MIB."
    MODULE -- this module
    MANDATORY-GROUPS {
                     ocStbHostSystemGroup,
                     ocStbHostSoftwareGroup,
                     ocStbHostStatusGroup,
                     ocStbHostSecuritySubSystemGroup
                     }
    OBJECT ocStbHostSystemMemoryReportMemoryType
    DESCRIPTION
            "Retired values internalHardDriveNoDrmSupport(6)."

     OBJECT ocStbHostSoftwareStatus
     DESCRIPTION
             "Retired values replaced by more
             descriptive values:
               active(1),
               inactive(2),
               downloading(3)."
     ::= { ocStbHostMIBCompliances 1 }

ocStbHostSystemGroup OBJECT-GROUP
    OBJECTS     {
                ocStbHostSerialNumber,
                ocStbHostHostID,
                ocStbHostCapabilities,
                ocStbHostAvcSupport,
                ocStbHostAVInterfaceType,
                ocStbHostAVInterfaceDesc,
                ocStbHostAVInterfaceStatus,
                ocStbHostInBandTunerModulationMode,
                ocStbHostInBandTunerFrequency,
                ocStbHostInBandTunerInterleaver,
                ocStbHostInBandTunerPower,
                ocStbHostInBandTunerAGCValue,
                ocStbHostInBandTunerSNRValue,
                ocStbHostInBandTunerUnerroreds,
                ocStbHostInBandTunerCorrecteds,
                ocStbHostInBandTunerUncorrectables,
                ocStbHostInBandTunerCarrierLockLost,
                  ocStbHostInBandTunerPCRErrors,
                  ocStbHostInBandTunerPTSErrors,
                  ocStbHostInBandTunerState,
                  ocStbHostInBandTunerBER,
                  ocStbHostInBandTunerSecsSinceLock,
                  ocStbHostInBandTunerEqGain,
                  ocStbHostInBandTunerMainTapCoeff,
                  ocStbHostInBandTunerTotalTuneCount,
                  ocStbHostInBandTunerTuneFailureCount,
                  ocStbHostInBandTunerTuneFailFreq,
                  ocStbHostInBandTunerBandwidth,
                  ocStbHostIEEE1394ActiveNodes,
                  ocStbHostIEEE1394DataXMission,
                  ocStbHostIEEE1394DTCPStatus,
                  ocStbHostIEEE1394LoopStatus,
                  ocStbHostIEEE1394RootStatus,
                  ocStbHostIEEE1394CycleIsMaster,
                  ocStbHostIEEE1394IRMStatus,
                  ocStbHostIEEE1394AudioMuteStatus,
                  ocStbHostIEEE1394VideoMuteStatus,
                  ocStbHostIEEE1394ConnectedDevicesAVInterfaceIndex,
                  ocStbHostIEEE1394ConnectedDevicesSubUnitType,
                  ocStbHostIEEE1394ConnectedDevicesEui64,
                  ocStbHostIEEE1394ConnectedDevicesADSourceSelectSupport,
                  ocStbHostDVIHDMIOutputType,
                  ocStbHostDVIHDMIConnectionStatus,
                  ocStbHostDVIHDMIRepeaterStatus,
                  ocStbHostDVIHDMIVideoXmissionStatus,
                  ocStbHostDVIHDMIHDCPStatus,
                  ocStbHostDVIHDMIHostDeviceHDCPStatus,
                  ocStbHostDVIHDMIVideoMuteStatus,
                  ocStbHostDVIHDMIOutputFormat,
                  ocStbHostDVIHDMIAspectRatio,
                  ocStbHostDVIHDMIAudioFormat,
                  ocStbHostDVIHDMIAudioSampleRate,
                  ocStbHostDVIHDMIAudioChannelCount,
                  ocStbHostDVIHDMIAudioMuteStatus,
                  ocStbHostDVIHDMIAudioSampleSize,
                  ocStbHostDVIHDMIColorSpace,
                  ocStbHostDVIHDMIFrameRate,
                  ocStbHostDVIHDMIAttachedDeviceType,
                  ocStbHostDVIHDMIEdid,
                  ocStbHostDVIHDMILipSyncDelay,
                  ocStbHostDVIHDMICecFeatures,
                  ocStbHostDVIHDMIFeatures,
                  ocStbHostDVIHDMIMaxDeviceCount,
                  ocStbHostDVIHDMIEdidVersion,
                  ocStbHostDVIHDMI3DCompatibilityControl,
                  ocStbHostDVIHDMI3DCompatibilityMsgDisplay,
                  ocStbHostDVIHDMIPreferredVideoFormat,
                  ocStbHostDVIHDMIAvailableVideoFormat,
                  ocStbHostDVIHDMISupported3DStructures,
                  ocStbHostDVIHDMIActive3DStructure,
                  ocStbHostSPDIfAudioFormat,
                  ocStbHostSPDIfAudioMuteStatus,
                  ocStbHostComponentVideoConstrainedStatus,
                  ocStbHostComponentOutputFormat,
                  ocStbHostComponentAspectRatio,
                  ocStbHostComponentVideoMuteStatus,
                  ocStbHostRFChannelOut,
                  ocStbHostRFChannelOutAudioMuteStatus,
                  ocStbHostRFChannelOutVideoMuteStatus,
                  ocStbEasMessageStateCode,
                  ocStbEasMessageCountyCode,
                  ocStbEasMessageCountySubdivisionCode,
                  ocStbHostProgramAVSource,
                  ocStbHostProgramAVDestination,
                ocStbHostProgramContentSource,
                ocStbHostProgramContentDestination,
                ocStbHostMpeg2ContentProgramNumber,
                ocStbHostMpeg2ContentTransportStreamID,
                ocStbHostMpeg2ContentTotalStreams,
                ocStbHostMpeg2ContentSelectedVideoPID,
                ocStbHostMpeg2ContentSelectedAudioPID,
                ocStbHostMpeg2ContentOtherAudioPIDs,
                ocStbHostMpeg2ContentCCIValue,
                ocStbHostMpeg2ContentAPSValue,
                ocStbHostMpeg2ContentCITStatus,
                ocStbHostMpeg2ContentBroadcastFlagStatus,
                ocStbHostMpeg2ContentEPNStatus,
                ocStbHostMpeg2ContentPCRPID,
                ocStbHostMpeg2ContentPCRLockStatus,
                ocStbHostMpeg2ContentDecoderPTS,
                ocStbHostMpeg2ContentDiscontinuities,
                ocStbHostMpeg2ContentPktErrors,
                ocStbHostMpeg2ContentPipelineErrors,
                ocStbHostMpeg2ContentDecoderRestarts,
                ocStbHostQpskFDCFreq,
                ocStbHostQpskRDCFreq,
                ocStbHostQpskFDCBer,
                ocStbHostQpskFDCStatus,
                ocStbHostQpskFDCBytesRead,
                ocStbHostQpskFDCPower,
                ocStbHostQpskFDCLockedTime,
                ocStbHostQpskFDCSNR,
                ocStbHostQpskAGC,
                ocStbHostQpskRDCPower,
                ocStbHostQpskRDCDataRate,
                ocStbHostAnalogVideoProtectionStatus
                }
     STATUS     current
     DESCRIPTION
             "Defines the objects contained with the ocStbHost System
             Group."
     ::= { ocStbHostMIBGroups 1 }

ocStbHostSoftwareGroup OBJECT-GROUP
    OBJECTS      {
                 ocStbHostFirmwareImageStatus,
                 ocStbHostFirmwareCodeDownloadStatus,
                 ocStbHostFirmwareCodeObjectName,
                 ocStbHostFirmwareDownloadFailedStatus,
                 ocStbHostFirmwareDownloadFailedCount,
                 ocStbHostFirmwareDownloadGroupId,
                 ocStbHostSoftwareOCAPVersion,
                 ocStbHostSoftwareFirmwareReleaseDate,
                 ocStbHostSoftwareAppNameString,
                 ocStbHostSoftwareAppVersionNumber,
                 ocStbHostCCAppInfoIndex,
                 ocStbHostSoftwareFirmwareVersion,
                 ocStbHostCCApplicationName,
                 ocStbHostCCApplicationVersion,
                 ocStbHostSoftwareStatus,
                 ocStbHostSoftwareOrganizationId,
                 ocStbHostSoftwareApplicationId,
                 ocStbHostSoftwareApplicationInfoSigLastReceivedTime,
                 ocStbHostSoftwareApplicationInfoSigLastReadStatus,
                 ocStbHostSoftwareApplicationInfoSigLastNetworkVersionRead,
                 ocStbHostSoftwareApplicationInfoSigVersionInUse
                 }
    STATUS      current
    DESCRIPTION
            "The ocStbHost Software group."
    ::= { ocStbHostMIBGroups 2 }

ocStbHostStatusGroup OBJECT-GROUP
    OBJECTS      {
                 ocStbHostPowerStatus,
                 ocStbHostSystemTempDescr,
                 ocStbHostSystemTempValue,
                 ocStbHostSystemTempLastUpdate,
                 ocStbHostSystemTempMaxValue,
                 ocStbHostSystemMemoryReportMemoryType,
                 ocStbHostSystemMemoryReportMemorySize,
                 ocStbHostCardMacAddress,
                 ocStbHostCardIpAddressType,
                 ocStbHostCardIpAddress,
                 ocStbHostCCApplicationType,
                 ocStbHostCCAppInfoPage,
                 ocStbHostCardMfgId,
                 ocStbHostCardVersion,
                 ocStbHostCardRootOid,
                 ocStbHostCardSnmpAccessControl,
                 ocStbHostCfrSpecificationIssue,
                 ocStbHostMibSpecificationIssue,
                 ocStbHostPatTimeoutCount,
                 ocStbHostPmtTimeoutCount,
                 ocStbHostOobCarouselTimeoutCount,
                 ocStbHostInbandCarouselTimeoutCount,
                 ocStbHostCardSerialNumber,
                 ocStbHostCardId,
                 ocStbHostCardBindingStatus,
                 ocStbHostCardOpenedGenericResource,
                 ocStbHostCardTimeZoneOffset,
                 ocStbHostCardDaylightSavingsTimeDelta,
                 ocStbHostCardDaylightSavingsTimeEntry,
                 ocStbHostCardDaylightSavingsTimeExit,
                 ocStbHostCardEaLocationCode,
                 ocStbHostCardVctId,
                 ocStbHostCardCpAuthKeyStatus,
                 ocStbHostCardCpCertificateCheck,
                 ocStbHostCardCpCciChallengeCount,
                 ocStbHostCardCpKeyGenerationReqCount,
                 ocStbHostCardCpIdList,
                 ocStbHostIpAddressType,
                 ocStbHostIpSubNetMask,
                 ocStbHostOobMessageMode,
                 ocStbHostBootStatus,
                 ocStbHostDumpEventCount,
                 ocStbHostDumpNow,
                 ocStbHostDumpEventTimeout,
                 ocStbHostDumpFilePath,
                 ocStbHostRebootType,
                 ocStbHostRebootReset,
                 ocStbHostLargestAvailableBlock,
                 ocStbHostTotalVideoMemory,
                 ocStbHostAvailableVideoMemory,
                 ocStbHostJVMHeapSize,
                 ocStbHostJVMAvailHeap,
                 ocStbHostJVMLiveObjects,
                 ocStbHostJVMDeadObjects
                 }
    STATUS      current
    DESCRIPTION
            "The object group related to multiple ocStbHost status."
    ::= { ocStbHostMIBGroups 3 }

ocStbHostSecuritySubSystemGroup OBJECT-GROUP
    OBJECTS      {
                  ocStbHostCASystemIdentifier,
                  ocStbHostCAType
                  }
      STATUS     current
      DESCRIPTION
              "The ocStbHost Security Subsystem group."
      ::= { ocStbHostMIBGroups 4 }

ocStbHostNotificationGroup NOTIFICATION-GROUP
    NOTIFICATIONS {
                   ocStbPanicDumpTrap
                  }
    STATUS      current
    DESCRIPTION
            "Defines the objects contained with the ocStbHost System
            Group."
    ::= { ocStbHostMIBGroups 6 }

END
